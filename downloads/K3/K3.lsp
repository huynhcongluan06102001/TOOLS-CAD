;;; K3 standalone 0.1 - AutoCAD Windows. MLINE/LINE + pipe fitting blocks.
;;; No dependency on TC/HL namespace. Work on a copy; see README.
(vl-load-com)
(defun k3hl:add (a b) (mapcar '+ a b))
(defun k3hl:sub (a b) (mapcar '- a b))
(defun k3hl:mul (a s) (mapcar '(lambda (x) (* x s)) a))
(defun k3hl:dot (a b) (apply '+ (mapcar '* a b)))
(defun k3hl:zeros (n / out) (repeat n (setq out (cons 0.0 out))) out)
(defun k3hl:replace (xs i v / j) (setq j -1) (mapcar '(lambda (x) (setq j (1+ j)) (if (= i j) v x)) xs))
;;; Minimum-norm displacement satisfying A*x=b; dependent constraints checked.
(defun k3hl:solve (rows n / basis values row a b u c d norm x ok pair)
 (setq ok T x (k3hl:zeros n))
 (foreach row rows
  (setq a (car row) b (cadr row))
  (foreach pair basis
   (setq u (car pair) c (cadr pair) d (k3hl:dot a u)
    a (k3hl:sub a (k3hl:mul u d)) b (- b (* d c))))
  (setq norm (sqrt (k3hl:dot a a)))
  (if (> norm 0.00000001)
   (setq basis (append basis (list (list (k3hl:mul a (/ 1.0 norm)) (/ b norm)))))
   (if (> (abs b) 0.00001) (setq ok nil))))
 (if ok (progn (foreach pair basis (setq x (k3hl:add x (k3hl:mul (car pair) (cadr pair))))) x)))
(defun k3hl:row (terms value / r term)
 (setq r (k3hl:zeros (* 2 (length nodes))))
 (foreach term terms (setq r (k3hl:replace r (car term) (+ (nth (car term) r) (cadr term)))))
 (list r value))
(defun k3hl:node (p / i found q)
 (setq i 0)
 (foreach q nodes (if (<= (distance p q) tol) (setq found i)) (setq i (1+ i)))
 (if found found (progn (setq nodes (append nodes (list p))) (1- (length nodes)))))
(defun k3hl:vec (v) (vlax-safearray->list (vlax-variant-value v)))
(defun k3hl:array (v / a)
 (setq a (vlax-make-safearray vlax-vbDouble (cons 0 (1- (length v)))))
 (vlax-safearray-fill a v) a)
(defun k3hl:objects (s / i out)
 (setq i 0) (if s (repeat (sslength s) (setq out (cons (vlax-ename->vla-object (ssname s i)) out) i (1+ i)))) (reverse out))
(defun k3hl:ids (xs) (mapcar 'vla-get-Handle xs))
(defun k3hl:fail (s) (setq failure s) (exit))
(defun k3hl:inside (p lo hi)
 (and (<= (- (car lo) tol) (car p) (+ (car hi) tol)) (<= (- (cadr lo) tol) (cadr p) (+ (cadr hi) tol))))
(defun k3hl:disp (i solution) (list (nth (* 2 i) solution) (nth (1+ (* 2 i)) solution) 0.0))
(defun k3hl:work ( / net moving moveids objs nodes edges blocks groups tol obj kind data p q a b name lo hi ids i hits owners rows base target delta solution edge group id degree pin normal newa newb result snapshots record changed doc)
 (setq doc (vla-get-ActiveDocument (vlax-get-acad-object)))
 (if (/= (getvar "CTAB") "Model") (k3hl:fail "Chi ho tro Model space."))
 (prompt "\nK3: Chon TOAN BO mang lien ket can xu ly (MLINE/LINE + co/te/Y).")
 (setq net (ssget '((0 . "MLINE,LINE,INSERT") (410 . "Model"))))
 (if (null net) (exit))
 (if (> (sslength net) 100) (k3hl:fail "Chon cum cuc bo toi da 100 doi tuong."))
 (setq tol (getdist "\nSai so nhan dau noi <0.1>: ")) (if (null tol) (setq tol 0.1))
 (if (<= tol 0) (k3hl:fail "Sai so phai duong."))
 (setq objs (k3hl:objects net))
 (foreach obj objs
  (if (= (vla-get-Lock (vla-item (vla-get-Layers doc) (vla-get-Layer obj))) :vlax-true) (k3hl:fail "Mang co layer khoa."))
  (setq kind (vla-get-ObjectName obj))
  (cond
   ((member kind '("AcDbMline" "AcDbLine"))
    (if (= kind "AcDbMline")
     (progn (setq data (k3hl:vec (vla-get-Coordinates obj)))
      (if (/= (length data) 6) (k3hl:fail "Chi ho tro MLINE thang hai dinh."))
      (if (/= (vla-get-Justification obj) 1) (k3hl:fail "MLINE phai can tim Zero."))
      (setq p (list (nth 0 data) (nth 1 data) (nth 2 data)) q (list (nth 3 data) (nth 4 data) (nth 5 data))))
     (setq p (k3hl:vec (vla-get-StartPoint obj)) q (k3hl:vec (vla-get-EndPoint obj))))
    (if (or (> (abs (caddr p)) 0.000001) (> (abs (caddr q)) 0.000001) (<= (distance p q) tol)) (k3hl:fail "Can tuyen XY Z=0, chieu dai lon hon sai so."))
    (setq a (k3hl:node p) b (k3hl:node q) edges (cons (list obj a b p q) edges)))
   (T
    (setq name (strcase (if (vlax-property-available-p obj 'EffectiveName) (vla-get-EffectiveName obj) (vla-get-Name obj))))
    (if (not (wcmatch name "ELB*,TEE*,Y-*,RED*,SCREW-*,WELD-*")) (k3hl:fail (strcat "Block chua ho tro: " name ". Chi chon phu kien ong.")))
    (if (> (abs (caddr (k3hl:vec (vla-get-InsertionPoint obj)))) 0.000001) (k3hl:fail "Block phai Z=0."))
    (setq blocks (cons obj blocks)))))
 ;; Fitting envelope associations are restricted to the explicit selection.
 (setq groups nil owners nil)
 (foreach obj blocks
  (vla-GetBoundingBox obj 'lo 'hi) (setq lo (vlax-safearray->list lo) hi (vlax-safearray->list hi) ids nil i 0)
  (foreach p nodes
   (if (k3hl:inside p lo hi)
    (progn
     (if (assoc i owners) (k3hl:fail "Hai block cung bao mot dau ong. Tach cum/kiem tra block truoc."))
     (setq ids (cons i ids) owners (cons (cons i obj) owners))))
   (setq i (1+ i)))
  (if (or (< (length ids) 2) (> (length ids) 4)) (k3hl:fail "Khong nhan chac 2-4 cong noi cua block. Khong sua ban ve."))
  (setq groups (cons (list obj ids) groups)))
 (prompt "\nChon cum can TRUOT trong mang vua chon (ong va/hoac phu kien):")
 (setq moving (k3hl:objects (ssget '((0 . "MLINE,LINE,INSERT") (410 . "Model")))) moveids (k3hl:ids moving))
 (if (null moving) (exit))
 (foreach id moveids (if (not (member id (k3hl:ids objs))) (k3hl:fail "Cum truot phai nam trong mang da chon.")))
 (foreach edge edges
  (setq normal (k3hl:sub (nth 4 edge) (nth 3 edge)) normal (k3hl:mul normal (/ 1.0 (distance (nth 3 edge) (nth 4 edge)))) a (cadr edge) b (caddr edge))
  (setq rows (cons (k3hl:row (list (list (* 2 a) (- (cadr normal))) (list (1+ (* 2 a)) (car normal)) (list (* 2 b) (cadr normal)) (list (1+ (* 2 b)) (- (car normal)))) 0.0) rows))
  (foreach id (list a b) (setq degree (cons (cons id (1+ (if (assoc id degree) (cdr (assoc id degree)) 0))) degree)))
  (if (member (vla-get-Handle (car edge)) moveids) (setq pin (append pin (list a b)))))
 (foreach group groups
  (setq ids (cadr group) a (car ids))
  (foreach b (cdr ids)
   (setq rows (cons (k3hl:row (list (list (* 2 a) 1.0) (list (* 2 b) -1.0)) 0.0) rows)
    rows (cons (k3hl:row (list (list (1+ (* 2 a)) 1.0) (list (1+ (* 2 b)) -1.0)) 0.0) rows)))
  (if (member (vla-get-Handle (car group)) moveids) (setq pin (append pin ids))))
 (setq base (getpoint "\nDiem goc vector truot: ")) (if (null base) (exit))
 (setq target (getpoint base "\nDiem dich vector truot: ")) (if (null target) (exit))
 (setq delta (k3hl:sub (trans target 1 0) (trans base 1 0)))
 (if (> (abs (caddr delta)) 0.000001) (k3hl:fail "Chi truot trong mat phang XY."))
 (setq i 0)
 (foreach p nodes
  (cond
   ((member i pin) (setq rows (cons (k3hl:row (list (list (* 2 i) 1.0)) (car delta)) rows) rows (cons (k3hl:row (list (list (1+ (* 2 i)) 1.0)) (cadr delta)) rows)))
   ((and (= (cdr (assoc i degree)) 1) (not (assoc i owners)))
    (setq rows (cons (k3hl:row (list (list (* 2 i) 1.0)) 0.0) rows) rows (cons (k3hl:row (list (list (1+ (* 2 i)) 1.0)) 0.0) rows))))
  (setq i (1+ i)))
 (setq solution (k3hl:solve rows (* 2 (length nodes))))
 (if (null solution) (k3hl:fail "Vector nay mau thuan diem neo/huong ong. Thu vector khac hoac chon cum khac."))
 (foreach edge edges
  (setq p (nth 3 edge) q (nth 4 edge) newa (k3hl:add p (k3hl:disp (cadr edge) solution)) newb (k3hl:add q (k3hl:disp (caddr edge) solution)))
  (if (or (<= (distance newa newb) tol) (<= (k3hl:dot (k3hl:sub newb newa) (k3hl:sub q p)) 0)) (k3hl:fail "Ong bi dao chieu/qua ngan; huy thao tac."))
  (grdraw (trans newa 0 1) (trans newb 0 1) 3 1))
 (initget "Yes No")
 (setq result (getkword "\nDa ve tim moi mau xanh. Ap dung [Yes/No] <No>: ")) (redraw)
 (if (/= result "Yes") (exit))
 (if (= (logand (getvar "UNDOCTL") 1) 0) (k3hl:fail "Can bat UNDO truoc khi chay."))
 (vla-StartUndoMark doc)
 (setq result (vl-catch-all-apply '(lambda ()
  (foreach edge edges
   (setq obj (car edge) p (k3hl:add (nth 3 edge) (k3hl:disp (cadr edge) solution)) q (k3hl:add (nth 4 edge) (k3hl:disp (caddr edge) solution)))
   (setq snapshots (cons (list obj (nth 3 edge) (nth 4 edge)) snapshots))
   (if (= (vla-get-ObjectName obj) "AcDbMline") (vla-put-Coordinates obj (k3hl:array (append p q)))
    (progn (vla-put-StartPoint obj (vlax-3d-point p)) (vla-put-EndPoint obj (vlax-3d-point q)))))
  (foreach group groups
   (setq obj (car group) p (k3hl:vec (vla-get-InsertionPoint obj)) snapshots (cons (list obj p nil) snapshots))
   (vla-put-InsertionPoint obj (vlax-3d-point (k3hl:add p (k3hl:disp (car (cadr group)) solution)))))
 ) nil))
 (if (vl-catch-all-error-p result)
  (progn
   (foreach record snapshots
    (vl-catch-all-apply '(lambda ()
     (setq obj (car record))
     (cond ((null (caddr record)) (vla-put-InsertionPoint obj (vlax-3d-point (cadr record))))
      ((= (vla-get-ObjectName obj) "AcDbMline") (vla-put-Coordinates obj (k3hl:array (append (cadr record) (caddr record)))))
      (T (vla-put-StartPoint obj (vlax-3d-point (cadr record))) (vla-put-EndPoint obj (vlax-3d-point (caddr record)))))) nil))
   (princ (strcat "\nLoi: " (vl-catch-all-error-message result) ". Kiem tra ban ve, U neu can.")))
  (princ "\nK3: da truot theo rang buoc vector. U de hoan tac ca luot."))
 (vla-EndUndoMark doc) (vla-Regen doc 1))
(defun c:HLK3 ( / failure result)
 (setq result (vl-catch-all-apply 'k3hl:work nil)) (redraw)
 (if (vl-catch-all-error-p result) (princ (strcat "\nK3: " (if failure failure (vl-catch-all-error-message result))))) (princ))
(if (not (boundp 'c:K3)) (defun c:K3 () (c:HLK3)))
(princ "\nK3 standalone 0.1: lenh HLK3; K3 neu ten chua bi dung. Doc README truoc.")
(princ)
