;;; TOOLS CAD DUY - AutoCAD 2024 Windows - single-file delivery
;;; Version 0.9.0. Sources: 49 user-supplied VBA modules + template CAd Duy.dwg.
;;; APPLOAD this file, run TOOLS. TCTEMPLATE selects the user's DWG library.
;;; All program code + DCL are embedded here. No VBA enabler is required.
;;; DWG is an external data library, not embedded or modified by this program.
;;; Model / WCS XY / Z=0; default drawing units are millimetres.
;;; Pure-code checks run on Linux; AutoCAD/ActiveX/DCL host validation is pending.
;;; See docs/COVERAGE.md for differences, library limitations and acceptance steps.
(setq *tc-dcl-lines* (list
  "// Embedded into TOOLS-CAD_DUY.lsp by tools/build_release.py."
  "tc_main : dialog {"
  "  label = \"TOOLS CAD DUY | AutoCAD 2024 Windows\";"
  "  : row {"
  "    : boxed_column {"
  "      label = \"Nhom chuc nang\";"
  "      : list_box { key = \"groups\"; width = 23; height = 21; fixed_width = true; }"
  "    }"
  "    : boxed_column {"
  "      label = \"Lenh (nhap dup de chay)\";"
  "      : list_box { key = \"commands\"; width = 45; height = 21; fixed_width = true; }"
  "    }"
  "    : boxed_column {"
  "      label = \"Thong so dung chung\";"
  "      : popup_list { key = \"system\"; label = \"He\"; width = 30; }"
  "      : popup_list { key = \"material\"; label = \"Vat lieu\"; width = 30; }"
  "      : row {"
  "        : edit_box { key = \"dn\"; label = \"D/DN\"; edit_width = 7; }"
  "        : edit_box { key = \"width\"; label = \"W/D\"; edit_width = 7; }"
  "      }"
  "      : row {"
  "        : edit_box { key = \"height\"; label = \"H\"; edit_width = 7; }"
  "        : edit_box { key = \"text\"; label = \"Chu\"; edit_width = 7; }"
  "      }"
  "      : edit_box { key = \"layer\"; label = \"Layer\"; edit_width = 20; }"
  "      : edit_box { key = \"service\"; label = \"He thong\"; edit_width = 20; }"
  "      : edit_box { key = \"elevation\"; label = \"BOP/BOT\"; edit_width = 20; }"
  "      : row {"
  "        : edit_box { key = \"gap\"; label = \"Sai so noi\"; edit_width = 6; }"
  "        : edit_box { key = \"overlap\"; label = \"Ngam UPVC\"; edit_width = 6; }"
  "      }"
  "      : row {"
  "        : edit_box { key = \"fillet\"; label = \"R bo goc\"; edit_width = 6; }"
  "        : edit_box { key = \"rowtol\"; label = \"Sai so hang\"; edit_width = 6; }"
  "      }"
  "      : edit_box { key = \"allowance\"; label = \"Day cho/tuyen\"; edit_width = 10; }"
  "      : edit_box { key = \"unit\"; label = \"Don vi ve / met\"; edit_width = 10; }"
  "      : toggle { key = \"note\"; label = \"Ghi chu khi ve tuyen\"; }"
  "      : toggle { key = \"erase\"; label = \"Xoa nguon SAU khi chuyen doi\"; }"
  "      : text { label = \"Thep nhap DN; PPR/UPVC nhap D.\"; }"
  "    }"
  "  }"
  "  : text { key = \"hint\"; width = 104; fixed_width = true; }"
  "  : errtile { key = \"error\"; }"
  "  : row {"
  "    : button { key = \"run\"; label = \"Chay lenh\"; is_default = true; width = 18; }"
  "    : button { key = \"save\"; label = \"Luu thong so\"; width = 18; }"
  "    : button { key = \"help\"; label = \"Huong dan\"; width = 18; }"
  "    : button { key = \"cancel\"; label = \"Dong\"; is_cancel = true; width = 18; }"
  "  }"
  "}"
  ""
  "tc_blocks : dialog {"
  "  label = \"Thu vien block | template CAd Duy\";"
  "  : text { label = \"Doc truc tiep danh muc block; giu nguyen dinh nghia da co trong ban ve.\"; }"
  "  : row {"
  "    : edit_box { key = \"query\"; label = \"Loc ten (* = bat ky)\"; edit_width = 45; }"
  "    : button { key = \"filter\"; label = \"Loc\"; width = 12; }"
  "  }"
  "  : list_box { key = \"blocks\"; width = 76; height = 22; }"
  "  : text { key = \"count\"; width = 76; }"
  "  : errtile { key = \"error\"; }"
  "  ok_cancel;"
  "}"
))

;;; ===== tc-geometry =====
;;; Pure planar geometry, millimetres / WCS. No AutoCAD database calls here.
(defun tc:v+ (a b) (mapcar '+ a b))
(defun tc:v- (a b) (mapcar '- a b))
(defun tc:v* (a s) (mapcar '(lambda (x) (* x s)) a))
(defun tc:dot (a b) (apply '+ (mapcar '* a b)))
(defun tc:len (a) (sqrt (tc:dot a a)))
(defun tc:dist (a b) (tc:len (tc:v- a b)))
(defun tc:unit (a / n) (setq n (tc:len a)) (if (> n 0.000000001) (tc:v* a (/ 1.0 n))))
(defun tc:perp (a) (list (- (cadr a)) (car a) 0.0))
(defun tc:angle (a b / v) (setq v (tc:v- b a)) (atan (cadr v) (car v)))
(defun tc:polar (a ang len) (tc:v+ a (list (* len (cos ang)) (* len (sin ang)) 0.0)))
(defun tc:wrap (a)
  (while (> a pi) (setq a (- a (* 2.0 pi))))
  (while (<= a (- pi)) (setq a (+ a (* 2.0 pi)))) a)
(defun tc:turn (a b c) (tc:wrap (- (tc:angle b c) (tc:angle a b))))
(defun tc:elbow-rotation (a b c / d ang)
  ;; Same native elbow orientation as VEONGPPR/VEMANGCAP VBA.
  (setq d (tc:turn a b c) ang (tc:angle a b))
  (+ ang (if (> d 0.0) (abs d) pi)))
(defun tc:corner (a b c / d)
  (setq d (abs (* 180.0 (/ (tc:turn a b c) pi))))
  (cond ((< d 0.01) 0) ((< (abs (- d 45.0)) 0.1) 45)
        ((< (abs (- d 90.0)) 0.1) 90) (T nil)))
(defun tc:project (p a b clamp / v den u)
  (setq v (tc:v- b a) den (tc:dot v v))
  (if (< den 0.000000000001) a
    (progn (setq u (/ (tc:dot (tc:v- p a) v) (float den)))
      (if clamp (setq u (max 0.0 (min 1.0 u)))) (tc:v+ a (tc:v* v u)))))
(defun tc:on-segment (p a b tol) (<= (tc:dist p (tc:project p a b T)) tol))
(defun tc:intersection (a b c d / v w den s u)
  ;; Infinite 2D line intersection. Caller checks segment/gap limits.
  (setq v (tc:v- b a) w (tc:v- d c)
        den (- (* (car v) (cadr w)) (* (cadr v) (car w))))
  (if (> (abs den) 0.0000000001)
    (progn (setq s (tc:v- c a)
      u (/ (- (* (car s) (cadr w)) (* (cadr s) (car w))) (float den)))
      (tc:v+ a (tc:v* v u)))))
(defun tc:line-angle (a b c d / ang)
  (setq ang (abs (tc:wrap (- (tc:angle a b) (tc:angle c d)))))
  (if (> ang (/ pi 2.0)) (- pi ang) ang))
(defun tc:near-end (p a b) (if (< (tc:dist p a) (tc:dist p b)) a b))
(defun tc:far-end (p a b) (if (> (tc:dist p a) (tc:dist p b)) a b))
(defun tc:dedup (pts / out p)
  (foreach p pts (if (or (null out) (> (tc:dist p (car out)) 0.0000001)) (setq out (cons p out))))
  (reverse out))
(defun tc:simplify (pts / out p)
  (foreach p (tc:dedup pts)
    (while (and (cadr out) (equal (tc:corner (cadr out) (car out) p) 0))
      (setq out (cdr out))) (setq out (cons p out))) (reverse out))
(defun tc:chunks (flat n / out item)
  (while flat (setq item nil)
    (repeat n (setq item (cons (car flat) item) flat (cdr flat)))
    (setq out (cons (reverse item) out))) (reverse out))
(defun tc:replace-nth (n val xs / i)
  (setq i -1) (mapcar '(lambda (x) (setq i (1+ i)) (if (= i n) val x)) xs))
(defun tc:sort (items compare)
  ;; vl-sort can remove equal items; sorting indices preserves every selected item.
  (mapcar '(lambda (i) (nth i items)) (vl-sort-i items compare)))
(defun tc:nearest-order (pts start / out best p)
  ;; Remove exactly one occurrence; duplicate insertion points are preserved.
  (setq out (list start))
  (while pts
    (setq best (car pts))
    (foreach p (cdr pts) (if (< (tc:dist start p) (tc:dist start best)) (setq best p)))
    (setq pts (tc:remove-one best pts) out (cons best out) start best)) (reverse out))
(defun tc:remove-one (item xs)
  (cond ((null xs) nil) ((equal item (car xs)) (cdr xs))
        (T (cons (car xs) (tc:remove-one item (cdr xs))))))
(defun tc:row-order (pts tol / rows row p found result rev anchor)
  ;; Group by a fixed row anchor, avoiding a non-transitive sort comparator.
  (setq pts (tc:sort pts '(lambda (a b) (if (equal (cadr a) (cadr b) 0.00000001)
                             (< (car a) (car b)) (> (cadr a) (cadr b))))))
  (foreach p pts
    (if (and row (<= (abs (- (cadr p) anchor)) tol))
      (setq row (cons p row))
      (progn (if row (setq rows (cons row rows))) (setq row (list p) anchor (cadr p)))))
  (if row (setq rows (cons row rows)))
  (foreach row (reverse rows)
    (setq row (tc:sort row '(lambda (a b) (< (car a) (car b)))))
    (if rev (setq row (reverse row)))
    (setq result (append result row) rev (not rev))) result)
(defun tc:ortho-route (pts / out a b)
  (if pts (progn (setq a (car pts) out (list a))
    (foreach b (cdr pts)
      (setq out (append out (list (list (car b) (cadr a) (caddr a)) b)) a b))))
  (tc:dedup out))
(defun tc:grid (a b cols rows / dx dy x y i j pts)
  ;; Centred cell spacing; single row/column stays at centre.
  (setq dx (/ (abs (- (car b) (car a))) (float cols))
        dy (/ (abs (- (cadr b) (cadr a))) (float rows)) i 0)
  (repeat rows (setq j 0)
    (repeat cols (setq pts (cons (list (+ (min (car a) (car b)) (* (+ j 0.5) dx))
                       (+ (min (cadr a) (cadr b)) (* (+ i 0.5) dy)) (caddr a)) pts) j (1+ j)))
    (setq i (1+ i))) (reverse pts))
(defun tc:intervals (intervals lo hi / sorted out a b iv)
  ;; Union and clamp cut intervals to the original segment.
  (setq sorted (tc:sort intervals '(lambda (x y) (< (car x) (car y)))))
  (foreach iv sorted
    (setq a (max lo (car iv)) b (min hi (cadr iv)))
    (if (> b a)
      (if (and out (<= a (+ (cadar out) 0.0000001)))
        (setq out (cons (list (caar out) (max b (cadar out))) (cdr out)))
        (setq out (cons (list a b) out))))) (reverse out))
(defun tc:complement (intervals lo hi / out iv cursor)
  (setq cursor lo)
  (foreach iv (tc:intervals intervals lo hi)
    (if (> (- (car iv) cursor) 0.000001) (setq out (cons (list cursor (car iv)) out)))
    (setq cursor (cadr iv)))
  (if (> (- hi cursor) 0.000001) (setq out (cons (list cursor hi) out))) (reverse out))
(defun tc:steel-d (dn) (cdr (assoc (fix dn) '((15 . 21.0) (20 . 27.0) (25 . 34.0)
  (32 . 42.0) (40 . 49.0) (50 . 60.0) (65 . 76.0) (80 . 90.0)
  (100 . 114.0) (125 . 141.0) (150 . 168.0)))))
(defun tc:dn-values (system)
  (cond ((= system "PPR") '(20 25 32 40 50 63 75 90 110 125))
        ((= system "UPVC") '(21 27 34 42 49 60 75 90 114 140 168 220 280))
        (T '(15 20 25 32 40 50 65 80 100 125 150))))
(defun tc:steel-dn (diam / found pair)
  (foreach pair '((15 . 21.0) (20 . 27.0) (25 . 34.0) (32 . 42.0) (40 . 49.0)
      (50 . 60.0) (65 . 76.0) (80 . 90.0) (100 . 114.0) (125 . 141.0) (150 . 168.0))
    (if (< (abs (- diam (cdr pair))) 0.1) (setq found (car pair)))) found)
(defun tc:elbow-name (system material dn degrees / d prefix suffix)
  (setq d (rtos dn 2 0))
  (cond ((= system "TRAY") (strcat "Elbow " (if (= degrees 45) "45 " "") material))
        ((= system "DUCT") (strcat "Co " (if (= (strcase material) "TRON") "tron " "")
          (itoa degrees) (cond ((wcmatch (strcase material) "*TIEU AM*") " tieu am")
                             ((wcmatch (strcase material) "*CACH NHIET*") " cach nhiet") (T ""))))
        ((= system "STEEL") (strcat (if (< dn 60) "SCREW-" "WELD-") "ELB"
          (itoa degrees) "-DN" d))
        (T (strcat "ELB" (itoa degrees) "-D" d (if (= system "PPR") (strcat " " material) "")))))
(defun tc:branch-name (system material kind d1 d2 / stem)
  (setq stem (strcat (if (= system "STEEL") (if (< d1 60) "SCREW-" "WELD-") "")
    kind (if (= system "STEEL") "-DN" "-D") (rtos d1 2 0) "x" (rtos d2 2 0)))
  (if (= system "PPR") (strcat stem " " material) stem))
(defun tc:trunk-fitting-name (system material kind / suffix)
  (if (= system "TRAY")
    (cond ((= kind "RED") (strcat "Reducer " material))
          ((= kind "TEE") (strcat "Tee " material))
          ((= kind "CROSS") (strcat "Cross " material)))
    (progn (setq suffix (cond ((wcmatch (strcase material) "*TIEU AM*") " tieu am")
      ((wcmatch (strcase material) "*CACH NHIET*") " cach nhiet") (T "")))
      (cond ((= kind "RED") (if (= (strcase material) "TRON") "Con tron giam" (strcat "Con giam deu" suffix)))
            ((= kind "TEE") (if (= (strcase material) "TRON") "Chac chu T" (strcat "Chac 3" suffix)))
            ((= kind "Y") "Chac chu Y")))))
(princ)

;;; ===== tc-core =====
;;; Runtime, configuration, COM helpers and command transaction boundary.
(vl-load-com)
(setq *tc-version* "0.9.0")
(setq *tc-defaults* '((system . "PPR") (material . "PPR") (dn . 25.0) (width . 200.0)
  (height . 100.0) (layer . "TC_PPR") (service . "CW") (elevation . "0")
  (text . 100.0) (overlap . 20.0) (gap . 150.0) (rowtol . 100.0)
  (fillet . 100.0) (drop . 300.0) (allowance . 0.0) (scale . 1.0)
  (unit . 1000.0) (erase . "0") (note . "1") (steeljoint . "AUTO")))
(if (not (boundp '*tc-settings*)) (setq *tc-settings* *tc-defaults*))
(defun tc:cfg (key) (cdr (assoc key *tc-settings*)))
(defun tc:set (key value / pair)
  (if (setq pair (assoc key *tc-settings*))
    (setq *tc-settings* (subst (cons key value) pair *tc-settings*))))
(defun tc:save-config () (setenv "TOOLS_CAD_SETTINGS" (vl-prin1-to-string *tc-settings*)))
(defun tc:read-config ( / text data pair default)
  (if (setq text (getenv "TOOLS_CAD_SETTINGS"))
    (progn (setq data (vl-catch-all-apply 'read (list text)))
      (if (and (not (vl-catch-all-error-p data)) (eq (type data) 'LIST))
        (foreach default *tc-defaults*
          (setq pair (assoc (car default) data))
          (if (and pair (eq (type (cdr default)) (type (cdr pair)))
                   (or (not (eq (type (cdr pair)) 'REAL)) (> (cdr pair) 0.0)
                       (member (car pair) '(allowance overlap))))
            (tc:set (car pair) (cdr pair))))))))
(defun tc:doc () (vla-get-ActiveDocument (vlax-get-acad-object)))
(defun tc:space () (vla-get-ModelSpace (tc:doc)))
(defun tc:obj (e) (vlax-ename->vla-object e))
(defun tc:ename (o) (vlax-vla-object->ename o))
(defun tc:variant-list (x / result)
  (cond ((eq (type x) 'VARIANT) (tc:variant-list (vlax-variant-value x)))
        ((eq (type x) 'SAFEARRAY)
          (setq result (vl-catch-all-apply 'vlax-safearray->list (list x)))
          (if (vl-catch-all-error-p result) nil result)) (T x)))
(defun tc:array (xs kind / arr)
  (setq arr (vlax-make-safearray kind (cons 0 (1- (length xs)))))
  (vlax-safearray-fill arr xs) arr)
(defun tc:3d (p) (vlax-3d-point p))
(defun tc:touch () (setq *tc-dirty* T))
(defun tc:new (o) (tc:touch) o)
(defun tc:delete (o) (vla-delete o) (tc:touch))
(defun tc:fail (message) (setq *tc-failure* message) (exit))
(defun tc:model-check ()
  (if (= (getvar "CVPORT") 1) (tc:fail "Hay chuyen sang Model space truoc khi chay lenh.")))
(defun tc:point (message / p)
  (if (setq p (getpoint message)) (tc:xy-check (trans p 1 0))))
(defun tc:next-point (base message / p)
  (if (setq p (getpoint (trans base 0 1) message)) (tc:xy-check (trans p 1 0))))
(defun tc:xy-check (p)
  (if (> (abs (caddr p)) 0.000001) (tc:fail "Chi ho tro mat phang WCS XY, cao do hinh hoc Z=0.")) p)
(defun tc:positive (message value / x)
  (initget 6) (if (setq x (getreal (strcat message " <" (rtos value 2 2) ">: "))) x value))
(defun tc:integer (message value / x)
  (initget 6) (if (setq x (getint (strcat message " <" (itoa value) ">: "))) x value))
(defun tc:choose (message choices default / x)
  (initget choices) (if (setq x (getkword (strcat message " <" default ">: "))) x default))
(defun tc:selection (filter / ss i result)
  (prompt "\nChon doi tuong: ")
  (if (setq ss (ssget (append filter (list (cons 410 "Model")))))
    (progn (setq i 0) (repeat (sslength ss)
      (setq result (cons (tc:obj (ssname ss i)) result) i (1+ i))))) (reverse result))
(defun tc:pick (message types / hit obj)
  (if (setq hit (entsel message))
    (progn (setq obj (tc:obj (car hit)))
      (if (and types (not (member (vla-get-ObjectName obj) types)))
        (tc:fail "Loai doi tuong khong phu hop."))
      (if (/= (cdr (assoc 410 (entget (car hit)))) "Model") (tc:fail "Chi chon doi tuong Model space."))
      obj)))
(defun tc:layer (name color / layers obj)
  (if (or (= name "") (not (snvalid name))) (tc:fail "Ten layer khong hop le."))
  (setq layers (vla-get-Layers (tc:doc)))
  (if (tblsearch "LAYER" name) (setq obj (vla-item layers name))
    (progn (setq obj (tc:new (vla-add layers name))) (vla-put-Color obj color)))
  (if (or (= (vla-get-Lock obj) :vlax-true) (= (vla-get-Freeze obj) :vlax-true)
          (= (vla-get-LayerOn obj) :vlax-false))
    (tc:fail (strcat "Layer dang khoa/tat/dong bang: " name))) name)
(defun tc:writable (o / layer)
  (setq layer (vla-item (vla-get-Layers (tc:doc)) (vla-get-Layer o)))
  (if (= (vla-get-Lock layer) :vlax-true) (tc:fail "Doi tuong tren layer khoa.")) o)
(defun tc:put-layer (o layer) (vla-put-Layer o layer) (vla-put-Color o 256) o)
(defun tc:name (o) (if (vlax-property-available-p o 'EffectiveName) (vla-get-EffectiveName o) (vla-get-Name o)))
(defun tc:insertion (o) (tc:variant-list (vla-get-InsertionPoint o)))
(defun tc:dynprops (o)
  (if (and (vlax-property-available-p o 'IsDynamicBlock) (= (vla-get-IsDynamicBlock o) :vlax-true))
    (tc:variant-list (vla-GetDynamicBlockProperties o))))
(defun tc:dyn (o key / result p)
  (foreach p (tc:dynprops o)
    (if (= (strcase key) (strcase (vla-get-PropertyName p))) (setq result (vlax-variant-value (vla-get-Value p))))) result)
(defun tc:width-key (o)
  (cond ((numberp (tc:dyn o "Width1")) "Width1")
        ((numberp (tc:dyn o "Diameter")) "Diameter")
        ((numberp (tc:dyn o "Diameter1")) "Diameter1")
        (T (tc:fail (strcat "Block " (tc:name o) " thieu Width1/Diameter/Diameter1.")))))
(defun tc:second-width-key (o)
  (cond ((numberp (tc:dyn o "Width2")) "Width2")
        ((numberp (tc:dyn o "Diameter2")) "Diameter2")))
(defun tc:state (o state required / prop vals val found)
  ;; Visibility parameter labels vary. Resolve the property by its allowed state.
  (foreach prop (tc:dynprops o)
    (setq vals (tc:variant-list (vla-get-AllowedValues prop)))
    (foreach val vals
      (if (eq (type val) 'VARIANT) (setq val (vlax-variant-value val)))
      (if (and (eq (type val) 'STR) (= (strcase val) (strcase state)))
        (progn (tc:set-dyn o (vla-get-PropertyName prop) val T) (setq found T)))))
  (if (and required (not found)) (tc:fail (strcat "Block thieu trang thai " state))) found)
(defun tc:set-dyn (o key value required / found p allowed converted result)
  (foreach p (tc:dynprops o)
    (if (= (strcase key) (strcase (vla-get-PropertyName p)))
      (progn
        (if (= (vla-get-ReadOnly p) :vlax-true) (tc:fail (strcat "Dynamic property chi doc: " key)))
        (setq allowed (tc:variant-list (vla-get-AllowedValues p)))
        (if (and allowed (not (vl-some '(lambda (v) (equal (if (eq (type v) 'VARIANT) (vlax-variant-value v) v) value 0.000001)) allowed)))
          (tc:fail (strcat "Gia tri khong nam trong AllowedValues cua " key ": " (vl-princ-to-string value))))
        (setq converted (vlax-make-variant value (vlax-variant-type (vla-get-Value p))))
        (vla-put-Value p converted) (tc:touch) (vla-update o)
        (if (not (equal (tc:dyn o key) value 0.000001)) (tc:fail (strcat "Block tu choi gia tri " key)))
        (setq found T))))
  (if (and required (not found)) (tc:fail (strcat "Block " (tc:name o) " thieu property " key))) found)
(defun tc:attributes (o / out a)
  (if (and (vlax-property-available-p o 'HasAttributes) (= (vla-get-HasAttributes o) :vlax-true))
    (foreach a (tc:variant-list (vla-GetAttributes o))
      (setq out (cons (cons (strcase (vla-get-TagString a)) (vla-get-TextString a)) out)))) (reverse out))
(defun tc:set-attributes (o pairs / a pair)
  (if (= (vla-get-HasAttributes o) :vlax-true)
    (foreach a (tc:variant-list (vla-GetAttributes o))
      (if (setq pair (assoc (strcase (vla-get-TagString a)) pairs))
        (progn (vla-put-TextString a (cdr pair)) (tc:touch))))) o)
(defun tc:size-label (w h) (strcat "W" (rtos w 2 0) "xH" (rtos h 2 0)))
(defun tc:block-height (o fallback / pair pos height text)
  (foreach pair (tc:attributes o)
    (setq text (strcase (cdr pair)) pos (vl-string-search "XH" text))
    (if pos (progn (setq height (atof (substr text (+ pos 3))))
      (if (> height 0.0) (setq fallback height))))) fallback)
(defun tc:inherit-service (o source / key value)
  (foreach key '("SYSTEM" "TC_ELEVATION")
    (if (setq value (tc:xget source key)) (tc:xset o key value))))
(defun tc:size-attributes (o w h / tag val)
  (setq val (tc:size-label w h))
  (tc:set-attributes o (mapcar '(lambda (tag) (cons tag val)) '("SIZE" "CABLETRAY" "TRUNKING" "LADDER" "DUCT"))))
(defun tc:xset (o key value / e data)
  (regapp key) (setq e (tc:ename o) data (entget e))
  (entmod (append data (list (list -3 (list key (cons 1000 value)))))) (tc:touch) value)
(defun tc:xget (o key / data app)
  (if (setq data (assoc -3 (entget (tc:ename o) (list key))))
    (cdr (assoc 1000 (cdadr data)))))
(defun tc:metadata (o system material dn w h / item)
  (foreach item (list (cons "TC_SYSTEM" system) (cons "VAT LIEU" material)
      (cons "SYSTEM" (tc:cfg 'service)) (cons "TC_DN" (rtos dn 2 3))
      (cons "TC_WIDTH" (rtos w 2 3)) (cons "TC_HEIGHT" (rtos h 2 3))
      (cons "TC_ELEVATION" (tc:cfg 'elevation)))
    (tc:xset o (car item) (cdr item))) o)
(defun tc:polyline (pts layer / obj flat)
  (setq pts (tc:dedup pts))
  (if (< (length pts) 2) (tc:fail "Tuyen can it nhat hai diem khac nhau."))
  (setq flat (apply 'append (mapcar '(lambda (p) (list (car p) (cadr p))) pts)))
  (setq obj (tc:new (vla-AddLightWeightPolyline (tc:space) (tc:array flat vlax-vbDouble))))
  (tc:put-layer obj layer) obj)
(defun tc:poly-points (o / e data pts pair)
  (if (/= (vla-get-ObjectName o) "AcDbPolyline") (tc:fail "Can LWPOLYLINE."))
  (if (= (vla-get-Closed o) :vlax-true) (tc:fail "Chi ho tro polyline mo."))
  (setq e (tc:ename o) data (entget e))
  (if (not (equal (cdr (assoc 210 data)) '(0.0 0.0 1.0) 0.00000001)) (tc:fail "Polyline phai nam tren WCS XY."))
  (foreach pair data
    (if (and (= (car pair) 42) (> (abs (cdr pair)) 0.000000001)) (tc:fail "Polyline co cung tron: hay chia thanh cac doan thang truoc."))
    (if (= (car pair) 10) (setq pts (cons (tc:xy-check (trans (append (cdr pair) (list (vla-get-Elevation o))) e 0)) pts))))
  (tc:dedup (reverse pts)))
(defun tc:pick-route ( / p q pts)
  (if (setq p (tc:point "\nDiem dau (Enter huy): "))
    (progn (setq pts (list p))
      (while (setq q (tc:next-point p "\nDiem tiep theo (Enter ket thuc): "))
        (if (> (tc:dist p q) 0.000001) (setq pts (append pts (list q)) p q))))) pts)
(defun tc:temp-delete (o)
  (if (and o (not (vlax-object-released-p o))) (vl-catch-all-apply 'vla-delete (list o))))
(defun tc:cleanup ( / o)
  (foreach o *tc-temps* (tc:temp-delete o)) (setq *tc-temps* nil)
  (if (and *tc-dbx* (not (vlax-object-released-p *tc-dbx*))) (vlax-release-object *tc-dbx*)) (setq *tc-dbx* nil))
(defun tc:run (fn / *error* doc saved result pair undo-ended undo-started)
  (setq doc (tc:doc) *tc-dirty* nil *tc-failure* nil *tc-temps* nil)
  (setq saved (mapcar '(lambda (name) (cons name (getvar name)))
    '("CMDECHO" "CLAYER" "CMLSTYLE" "CMLSCALE" "CMLJUST" "FILLETRAD" "OSMODE")))
  (defun *error* (msg)
    (tc:cleanup)
    (foreach pair saved (vl-catch-all-apply 'setvar (list (car pair) (cdr pair))))
    (if (and undo-started (not undo-ended)) (vl-catch-all-apply 'vla-EndUndoMark (list doc)))
    (princ (strcat "\nTOOLS CAD: " msg " | Go U de hoan tac lenh neu can.")) (princ))
  (if (= (logand (getvar "UNDOCTL") 1) 0) (tc:fail "Bat UNDO truoc khi chay TOOLS CAD."))
  (tc:model-check) (vla-StartUndoMark doc) (setq undo-started T) (setvar "CMDECHO" 0)
  (setq result (vl-catch-all-apply fn nil))
  (tc:cleanup)
  (foreach pair saved (vl-catch-all-apply 'setvar (list (car pair) (cdr pair))))
  (vla-EndUndoMark doc) (setq undo-ended T)
  (if (vl-catch-all-error-p result)
    (progn
      (if *tc-dirty* (command-s "_.U"))
      (princ (strcat "\nTOOLS CAD: " (if *tc-failure* *tc-failure* (vl-catch-all-error-message result))
        (if *tc-dirty* " | Da hoan tac thay doi cua lenh." ""))))) (princ))
(tc:read-config)
(princ)

;;; ===== tc-library =====
;;; Named blocks are imported on demand from the user's Duy template.
(defun tc:library-path ( / candidates path)
  (if (and (boundp '*tc-template*) *tc-template* (findfile *tc-template*)) *tc-template*
    (progn
      (setq *tc-template* nil)
      (setq candidates (list (getenv "TOOLS_CAD_TEMPLATE") (findfile "template CAd Duy.dwg")
        (strcat (getvar "DWGPREFIX") "template CAd Duy.dwg")))
      (if (boundp '*tc-root*) (setq candidates (append candidates
        (list (strcat *tc-root* "/library/template CAd Duy.dwg") (strcat *tc-root* "/template CAd Duy.dwg")))))
      (foreach path candidates (if (and path (null *tc-template*) (findfile path)) (setq *tc-template* (findfile path))))
      (if (null *tc-template*) (setq *tc-template* (getfiled "Chon template CAd Duy.dwg lam thu vien block" "" "dwg" 0)))
      (if *tc-template* (setenv "TOOLS_CAD_TEMPLATE" *tc-template*)) *tc-template*)))
(defun tc:select-template ( / path)
  (if (setq path (getfiled "Chon dung template CAd Duy.dwg" "" "dwg" 0))
    (progn (setq *tc-template* path) (setenv "TOOLS_CAD_TEMPLATE" path)
      (princ (strcat "\nThu vien: " path)))))
(defun tc:dbx ( / app version result)
  (if (null *tc-dbx*)
    (progn
      (if (null (tc:library-path)) (tc:fail "Chua chon template CAd Duy.dwg."))
      (setq app (vlax-get-acad-object) version (substr (getvar "ACADVER") 1 2)
        result (vl-catch-all-apply 'vla-GetInterfaceObject (list app (strcat "ObjectDBX.AxDbDocument." version))))
      (if (vl-catch-all-error-p result)
        (tc:fail "Khong khoi tao duoc ObjectDBX. Can AutoCAD 2024 Windows ban day du."))
      (setq *tc-dbx* result)
      (setq result (vl-catch-all-apply 'vla-Open (list *tc-dbx* (tc:library-path))))
      (if (vl-catch-all-error-p result) (tc:fail (strcat "Khong mo duoc template: " (vl-catch-all-error-message result))))))
  *tc-dbx*)
(defun tc:block-present (name) (not (null (tblsearch "BLOCK" name))))
(defun tc:ensure-block (name / src result)
  (if (not (tc:block-present name))
    (progn
      (setq src (vl-catch-all-apply 'vla-Item (list (vla-get-Blocks (tc:dbx)) name)))
      (if (vl-catch-all-error-p src) (tc:fail (strcat "Template Duy khong co block: " name ". Dung TCBLOCK de kiem tra.")))
      (if (= (vla-get-IsXRef src) :vlax-true) (tc:fail "Khong nhap block Xref."))
      (setq result (vla-CopyObjects *tc-dbx* (tc:array (list src) vlax-vbObject) (vla-get-Blocks (tc:doc))))
      (tc:touch)
      (if (not (tc:block-present name)) (tc:fail (strcat "Khong nhap duoc block " name))))) name)
(defun tc:block-names (source / out blk name)
  (vlax-for blk (vla-get-Blocks source)
    (setq name (vla-get-Name blk))
    (if (and (/= (substr name 1 1) "*") (= (vla-get-IsXRef blk) :vlax-false))
      (setq out (cons name out))))
  (acad_strlsort out))
(defun tc:insert (name pt rotation layer / o)
  (tc:ensure-block name)
  (setq o (tc:new (vla-InsertBlock (tc:space) (tc:3d (tc:xy-check pt)) name 1.0 1.0 1.0 rotation)))
  (tc:put-layer o layer) o)
(defun tc:mline-style ( / dict style offsets pair)
  ;; Own fixed +/-0.5 style; protects against templates with different MC offsets.
  (setq dict (cdr (assoc -1 (dictsearch (namedobjdict) "ACAD_MLINESTYLE"))))
  (if (null dict)
    (progn (setq dict (entmakex '((0 . "DICTIONARY") (100 . "AcDbDictionary") (281 . 1))))
      (dictadd (namedobjdict) "ACAD_MLINESTYLE" dict) (tc:touch)))
  (if (not (dictsearch dict "TC_MC"))
    (progn (setq style (entmakex '((0 . "MLINESTYLE") (100 . "AcDbMlineStyle")
      (2 . "TC_MC") (70 . 0) (3 . "TOOLS CAD centreline +/-0.5") (62 . 256)
      (51 . 1.5707963267949) (52 . 1.5707963267949) (71 . 2)
      (49 . 0.5) (62 . 256) (6 . "BYLAYER") (49 . -0.5) (62 . 256) (6 . "BYLAYER"))))
      (if (null style) (tc:fail "Khong tao duoc MLINESTYLE TC_MC."))
      (dictadd dict "TC_MC" style) (tc:touch)))
  (setq style (dictsearch dict "TC_MC") offsets nil)
  (foreach pair style (if (= (car pair) 49) (setq offsets (cons (cdr pair) offsets))))
  (if (not (and (= (length offsets) 2) (member 0.5 offsets) (member -0.5 offsets)))
    (tc:fail "MLINESTYLE TC_MC da co nhung khong phai hai net +/-0.5. Kiem tra style truoc."))
  (setvar "CMLSTYLE" "TC_MC") "TC_MC")
(defun tc:mline (a b diameter layer / o)
  (if (<= (tc:dist a b) 0.000001) (tc:fail "Doan ong qua ngan."))
  (tc:mline-style) (setvar "CMLSCALE" diameter) (setvar "CMLJUST" 1)
  (setq o (tc:new (vla-AddMLine (tc:space) (tc:array (append a b) vlax-vbDouble))))
  (vla-put-MLineScale o diameter) (vla-put-Justification o 1)
  (tc:put-layer o layer) o)
(defun tc:explode-temp (o depth / result child out)
  (if (> depth 6) (tc:fail "Block long qua 6 cap, can kiem tra thu vien."))
  (setq result (vl-catch-all-apply 'vlax-invoke (list o 'Explode)))
  (if (vl-catch-all-error-p result) (tc:fail (strcat "Block khong cho explode: " (tc:name o))))
  (setq *tc-temps* (append result *tc-temps*))
  (foreach child result
    (if (= (vla-get-Visible child) :vlax-true)
      (if (= (vla-get-ObjectName child) "AcDbBlockReference")
        (setq out (append out (tc:explode-temp child (1+ depth))))
        (if (member (vla-get-ObjectName child)
          '("AcDbLine" "AcDbPolyline" "AcDb2dPolyline" "AcDbArc" "AcDbCircle" "AcDbEllipse" "AcDbSpline"))
          (setq out (cons child out)))))) out)
(defun tc:port (fitting target overlap / center direction ray children child raw pts p best dist limit saved-temps low high reach)
  ;; Intersect a ray with the current evaluated visible geometry, not an axis-aligned box.
  (setq center (tc:insertion fitting) direction (tc:unit (tc:v- target center))
        limit (tc:dist center target) saved-temps *tc-temps*)
  (if (null direction) (tc:fail "Diem xa cua ong trung tam fitting."))
  (vla-GetBoundingBox fitting 'low 'high)
  (setq reach (* 2.0 (max limit (tc:dist center (tc:variant-list low)) (tc:dist center (tc:variant-list high)))))
  (setq ray (vla-AddLine (tc:space) (tc:3d center) (tc:3d (tc:v+ center (tc:v* direction reach)))))
  (setq *tc-temps* (cons ray *tc-temps*) children (tc:explode-temp fitting 0) dist -1.0)
  (foreach child children
    (setq raw (vl-catch-all-apply 'vla-IntersectWith (list ray child 0)))
    (if (not (vl-catch-all-error-p raw))
      (progn (setq pts (tc:variant-list raw))
        (foreach p (tc:chunks pts 3)
          (if (> (tc:dist center p) (+ dist 0.000001))
            (setq best p dist (tc:dist center p)))))))
  (while (not (eq *tc-temps* saved-temps))
    (tc:temp-delete (car *tc-temps*)) (setq *tc-temps* (cdr *tc-temps*)))
  (if (null best) (tc:fail (strcat "Khong xac dinh duoc cong noi cua " (tc:name fitting)
    ". Kiem tra huong block/Visibility hoac chieu dai doan ong.")))
  (if (>= dist (- limit 0.000001)) (tc:fail (strcat "Doan qua ngan cho fitting " (tc:name fitting))))
  (tc:v- best (tc:v* direction (min overlap (* 0.9 dist)))))
(defun tc:inspect ( / o p a)
  (if (setq o (tc:pick "\nChon block de doc thuoc tinh: " '("AcDbBlockReference")))
    (progn (princ (strcat "\nBlock: " (tc:name o)))
      (foreach p (tc:dynprops o)
        (princ (strcat "\n  " (vla-get-PropertyName p) " = " (vl-princ-to-string (vlax-variant-value (vla-get-Value p)))
          " | Allowed: " (vl-princ-to-string (tc:variant-list (vla-get-AllowedValues p))))))
      (foreach a (tc:attributes o) (princ (strcat "\n  @" (car a) " = " (cdr a))))
      (princ (strcat "\n  SYSTEM=" (if (tc:xget o "SYSTEM") (tc:xget o "SYSTEM") "")
        " | VAT LIEU=" (if (tc:xget o "VAT LIEU") (tc:xget o "VAT LIEU") ""))))))
(princ)

;;; ===== tc-mep =====
;;; Route generation and explicit block-name rules from the supplied VBA.
(defun tc:pipe-p (system) (member system '("PPR" "UPVC" "STEEL")))
(defun tc:diameter (system dn / diam)
  (if (and (tc:pipe-p system) (not (and (equal dn (float (fix dn)) 0.00001) (member (fix dn) (tc:dn-values system)))))
    (tc:fail (strcat "D/DN khong nam trong kich thuoc template: " (vl-princ-to-string (tc:dn-values system)))))
  (if (= system "STEEL")
    (if (setq diam (tc:steel-d dn)) diam (tc:fail "DN thep ho tro: 15,20,25,32,40,50,65,80,100,125,150.")) dn))
(defun tc:material (system)
  (cond ((= system "UPVC") "UPVC") ((= system "STEEL") "STK")
        ((= system "PPR") "PPR") ((= system "TRAY") (tc:cfg 'material)) (T (tc:cfg 'material))))
(defun tc:straight-name (system material)
  (cond ((= system "TRAY") material)
        ((= system "DUCT") (strcat "ONG GIO " material))))
(defun tc:prepare (system / material layer)
  (if (member (tc:cfg 'layer) '("TC_PPR" "TC_UPVC" "TC_STEEL" "TC_TRAY" "TC_DUCT"))
    (tc:set 'layer (strcat "TC_" system)))
  (tc:set 'system system)
  (cond ((= system "PPR") (tc:set 'material "PPR"))
    ((= system "UPVC") (tc:set 'material "UPVC"))
    ((= system "STEEL") (tc:set 'material "STK"))
    ((and (= system "TRAY") (not (member (tc:cfg 'material) '("Trunking" "Cable Tray" "Ladder")))) (tc:set 'material "Cable Tray"))
    ((and (= system "DUCT") (not (member (tc:cfg 'material) '("nep TDC" "nep C" "tron" "tieu am nep TDC" "cach nhiet nep TDC" "cach nhiet nep C")))) (tc:set 'material "nep TDC")))
  (if (tc:pipe-p system)
    (progn
      (if (not (member (fix (tc:cfg 'dn)) (tc:dn-values system))) (tc:set 'dn (if (= system "UPVC") 60.0 25.0)))
      (princ (strcat "\nKich thuoc co trong template: " (vl-princ-to-string (tc:dn-values system))))
      (tc:set 'dn (tc:positive "\nDuong kinh (thep nhap DN, nhua nhap D)" (tc:cfg 'dn))))
    (progn
      (if (= system "TRAY")
        (progn (prompt "\nVat lieu lay tu bang TOOLS: Cable Tray / Trunking / Ladder.")
          (setq material (getstring T (strcat "\nTen block thang <" (tc:cfg 'material) ">: ")))
          (if (/= material "") (tc:set 'material material)))
        (progn (setq material (getstring T (strcat "\nHau to block Ong gio (nep TDC/nep C/tron/tieu am nep TDC/cach nhiet nep TDC/cach nhiet nep C) <" (tc:cfg 'material) ">: ")))
          (if (/= material "") (tc:set 'material material))))
      (tc:set 'width (tc:positive "\nChieu rong/D ong gio tron" (tc:cfg 'width)))
      (tc:set 'height (tc:positive "\nChieu cao" (tc:cfg 'height)))))
  (setq layer (getstring T (strcat "\nLayer he thong <" (tc:cfg 'layer) ">: ")))
  (if (/= layer "") (tc:set 'layer layer))
  (tc:layer (tc:cfg 'layer) 3) (tc:save-config))
(defun tc:setup-fitting (o system material dn width width2 height / label)
  (if (tc:pipe-p system)
    (progn (tc:set-dyn o "DN" dn nil) (tc:state o "SIDE" nil))
    (progn (tc:set-dyn o (tc:width-key o) width T)
      (if (tc:second-width-key o) (tc:set-dyn o (tc:second-width-key o) width2 T)
        (if (not (equal width width2 0.01)) (tc:fail "Fitting khong co kich thuoc dau thu hai.")))
      (tc:size-attributes o width height)))
  (tc:metadata o system material dn width height) (vla-update o) o)
(defun tc:straight (a b system material dn width height layer / o diam)
  (setq a (tc:xy-check a) b (tc:xy-check b))
  (if (tc:pipe-p system)
    (setq o (tc:mline a b (tc:diameter system dn) layer))
    (progn
      (setq o (tc:insert (tc:straight-name system material) a (tc:angle a b) layer))
      (tc:set-dyn o (tc:width-key o) width T)
      (tc:set-dyn o "Length" (tc:dist a b) T)
      (tc:size-attributes o width height)))
  (tc:metadata o system material dn width height) o)
(defun tc:note (pts system material dn width height layer / a b p ang content obj)
  (if (= (tc:cfg 'note) "1")
    (progn (setq a (car pts) b (cadr pts) ang (tc:angle a b)
      p (tc:polar (tc:v* (tc:v+ a b) 0.5) (+ ang (/ pi 2.0)) (* 1.5 (tc:cfg 'text)))
      content (strcat material " " (if (tc:pipe-p system) (strcat (if (= system "STEEL") "DN" "D") (rtos dn 2 0))
        (tc:size-label width height)) " | " (tc:cfg 'service) " | BOP/BOT=" (tc:cfg 'elevation) " FFL")
      obj (tc:new (vla-AddText (tc:space) content (tc:3d p) (tc:cfg 'text))))
      (if (or (> ang (/ pi 2.0)) (< ang (- (/ pi 2.0)))) (setq ang (+ ang pi)))
      (vla-put-Rotation obj ang) (tc:put-layer obj layer))))
(defun tc:build-route (pts system / material dn width height layer fits i degree name fit a b p q left right overlap)
  (setq pts (tc:simplify pts) material (tc:material system) dn (tc:cfg 'dn)
    width (tc:cfg 'width) height (tc:cfg 'height) layer (tc:cfg 'layer)
    overlap (if (= system "UPVC") (tc:cfg 'overlap) 0.0))
  (if (< (length pts) 2) (tc:fail "Can it nhat hai diem de tao tuyen."))
  ;; Preflight every name and turn before adding the first run.
  (if (not (tc:pipe-p system)) (tc:ensure-block (tc:straight-name system material)))
  (tc:diameter system dn)
  (setq i 1 fits (list nil))
  (while (< i (1- (length pts)))
    (setq degree (tc:corner (nth (1- i) pts) (nth i pts) (nth (1+ i) pts)))
    (if (null degree) (tc:fail "Tuyen chi ho tro co 45/90 do. Hay sua goc lech hoac chia tuyen."))
    (setq name (tc:elbow-name system material dn degree)) (tc:ensure-block name)
    (setq fit (tc:insert name (nth i pts) (tc:elbow-rotation (nth (1- i) pts) (nth i pts) (nth (1+ i) pts)) layer))
    (tc:setup-fitting fit system material dn width width height)
    (setq fits (append fits (list fit)) i (1+ i)))
  (setq fits (append fits (list nil)) i 0)
  (while (< i (1- (length pts)))
    (setq a (nth i pts) b (nth (1+ i) pts) left (nth i fits) right (nth (1+ i) fits)
      p (if left (tc:port left b overlap) a) q (if right (tc:port right a overlap) b))
    (if (<= (tc:dot (tc:v- q p) (tc:unit (tc:v- b a))) 0.0001)
      (tc:fail "Doan qua ngan: hai fitting chong lan. Tang chieu dai tuyen."))
    (tc:straight p q system material dn width height layer) (setq i (1+ i)))
  (tc:note pts system material dn width height layer)
  (princ (strcat "\nDa tao " (itoa (1- (length pts))) " doan va " (itoa (- (length pts) 2)) " fitting.")))
(defun tc:draw (system / mode objs obj pts picked)
  (tc:prepare system)
  (setq mode (tc:choose "\nNguon tuyen [Pick/Polyline]" "Pick Polyline" "Pick"))
  (if (= mode "Polyline")
    (progn (setq objs (tc:selection '((0 . "LWPOLYLINE"))))
      ;; Validate all source geometry before constructing any route.
      (foreach obj objs (tc:poly-points obj))
      (foreach obj objs (tc:build-route (tc:poly-points obj) system)
        (if (= (tc:cfg 'erase) "1") (tc:delete (tc:writable obj)))))
    (if (and (setq picked (tc:pick-sized-route system)) (> (length (car picked)) 1))
      (progn (tc:build-sized-route (car picked) (cadr picked) system) (tc:save-config)))))
(defun tc:pick-sized-route (system / p q pts sizes dims guide)
  ;; Size applies to the next segment. At a straight size transition a reducer is inserted.
  (if (setq p (tc:point "\nDiem dau (Enter huy): "))
    (progn
      (setq pts (list p))
      (while (progn (initget "Size Back")
        (setq q (getpoint (trans p 0 1) "\nDiem tiep / [Size/Back] (Enter ket thuc): ")))
        (cond
          ((eq (type q) 'STR)
            (if (= q "Size")
              (if (tc:pipe-p system)
                (tc:set 'dn (tc:positive "\nD/DN cho doan tiep theo" (tc:cfg 'dn)))
                (progn (tc:set 'width (tc:positive "\nRong/D doan tiep theo" (tc:cfg 'width)))
                  (tc:set 'height (tc:positive "\nCao doan tiep theo" (tc:cfg 'height)))))
              (if (cdr pts)
                (setq pts (reverse (cdr (reverse pts))) sizes (reverse (cdr (reverse sizes))) p (last pts)))))
          (T (setq q (tc:xy-check (trans q 1 0)))
            (if (> (tc:dist p q) 0.000001)
              (setq pts (append pts (list q)) sizes (append sizes (list (list (tc:cfg 'dn) (tc:cfg 'width) (tc:cfg 'height)))) p q))))
        (if (> (length pts) 1)
          (if guide
            (vla-put-Coordinates guide (tc:array (apply 'append (mapcar '(lambda (pt) (list (car pt) (cadr pt))) pts)) vlax-vbDouble))
            (progn
              (setq guide (vla-AddLightWeightPolyline (tc:space) (tc:array (apply 'append (mapcar '(lambda (pt) (list (car pt) (cadr pt))) pts)) vlax-vbDouble)))
              (setq *tc-temps* (cons guide *tc-temps*)) (vla-put-Color guide 1)))
          (if guide (progn (tc:temp-delete guide) (setq *tc-temps* (vl-remove guide *tc-temps*) guide nil)))))
      (if guide (progn (tc:temp-delete guide) (setq *tc-temps* (vl-remove guide *tc-temps*)))))
    )
  (if pts (list pts sizes)))
(defun tc:sized-junction (system material previous current a b c / deg oldsize newsize name rot dn width1 width2 h)
  (setq deg (tc:corner a b c)
    oldsize (if (tc:pipe-p system) (car previous) (cadr previous))
    newsize (if (tc:pipe-p system) (car current) (cadr current)))
  (cond
    ((or (null deg) (and (/= deg 0) (not (equal oldsize newsize 0.01)))) 'unsupported)
    ((and (= deg 0) (equal oldsize newsize 0.01)) nil)
    (T
      (if (= deg 0)
        (setq name (if (tc:pipe-p system) (tc:branch-name system material "RED" (max oldsize newsize) (min oldsize newsize))
          (tc:trunk-fitting-name system material "RED"))
          rot (+ (tc:angle a b) (if (< oldsize newsize) pi 0.0)))
        (setq name (tc:elbow-name system material (car current) deg) rot (tc:elbow-rotation a b c)))
      (setq dn (max (car previous) (car current)) width1 (max (cadr previous) (cadr current))
        width2 (min (cadr previous) (cadr current)) h (max (caddr previous) (caddr current)))
      (list name rot dn width1 width2 h))))
(defun tc:build-sized-route (pts sizes system / material layer fits i spec fit a b p q overlap dims count)
  (setq material (tc:material system) layer (tc:cfg 'layer) fits (list nil) i 1 count 0
    overlap (if (= system "UPVC") (tc:cfg 'overlap) 0.0))
  (if (/= (length sizes) (1- (length pts))) (tc:fail "Du lieu kich thuoc tuyen khong khop so doan."))
  (if (not (tc:pipe-p system)) (tc:ensure-block (tc:straight-name system material)))
  (foreach dims sizes (tc:diameter system (car dims)))
  (while (< i (1- (length pts)))
    (setq spec (tc:sized-junction system material (nth (1- i) sizes) (nth i sizes)
      (nth (1- i) pts) (nth i pts) (nth (1+ i) pts)) fit nil)
    (if (eq spec 'unsupported) (tc:fail "Chi ho tro goc 45/90. Khi doi kich thuoc, tao mot doan thang rieng cho reducer."))
    (if spec
      (progn
        (setq fit (tc:insert (car spec) (nth i pts) (cadr spec) layer))
        (tc:setup-fitting fit system material (nth 2 spec) (nth 3 spec) (nth 4 spec) (nth 5 spec))
        (setq count (1+ count))))
    (setq fits (append fits (list fit)) i (1+ i)))
  (setq fits (append fits (list nil)) i 0)
  (while (< i (length sizes))
    (setq a (nth i pts) b (nth (1+ i) pts) dims (nth i sizes)
      p (if (nth i fits) (tc:port (nth i fits) b overlap) a)
      q (if (nth (1+ i) fits) (tc:port (nth (1+ i) fits) a overlap) b))
    (if (<= (tc:dot (tc:v- q p) (tc:unit (tc:v- b a))) 0.0001) (tc:fail "Hai fitting chong lan: doan qua ngan."))
    (tc:straight p q system material (car dims) (cadr dims) (caddr dims) layer)
    (if (or (= i 0) (not (equal dims (nth (1- i) sizes) 0.01)))
      (tc:note (list a b) system material (car dims) (cadr dims) (caddr dims) layer))
    (setq i (1+ i)))
  (princ (strcat "\nDa tao " (itoa (length sizes)) " doan, " (itoa count) " fitting; ho tro doi Size tren doan thang.")))
(defun tc:convert (system / objs obj)
  (tc:prepare system) (setq objs (tc:selection '((0 . "LWPOLYLINE"))))
  (foreach obj objs (tc:poly-points obj))
  (foreach obj objs (tc:build-route (tc:poly-points obj) system)
    (if (= (tc:cfg 'erase) "1") (tc:delete (tc:writable obj)))))
(defun tc:segment (o system / typ coords a b size dn width material h)
  (setq typ (vla-get-ObjectName o) material (tc:material system) h (tc:cfg 'height))
  (cond
    ((= typ "AcDbMline")
      (setq coords (tc:variant-list (vla-get-Coordinates o)))
      (if (/= (length coords) 6) (tc:fail "Noi tu dong chi ho tro MLINE 2 dinh."))
      (if (/= (vla-get-Justification o) 1) (tc:fail "MLINE phai co Justification = Zero (tam)."))
      (setq a (tc:xy-check (list (car coords) (cadr coords) (caddr coords))) b (tc:xy-check (cadr (tc:chunks coords 3)))
        width (abs (vla-get-MLineScale o)) dn (if (= system "STEEL") (tc:steel-dn width) width))
      (if (null dn) (tc:fail "Scale MLINE khong khop bang D/DN thep.")))
    ((= typ "AcDbBlockReference")
      (if (tc:pipe-p system) (tc:fail "Ong nhua/thep phai la MLINE."))
      (if (or (not (equal (vla-get-XScaleFactor o) 1.0 0.000001))
              (not (equal (vla-get-YScaleFactor o) 1.0 0.000001))
              (not (equal (tc:variant-list (vla-get-Normal o)) '(0.0 0.0 1.0) 0.00000001)))
        (tc:fail "Block thang phai co scale X=Y=1 va Normal WCS Z+."))
      (if (null (tc:dyn o "Length")) (tc:fail "Block thang thieu Length."))
      (setq a (tc:xy-check (tc:insertion o)) b (tc:polar a (vla-get-Rotation o) (tc:dyn o "Length"))
        width (tc:dyn o (tc:width-key o)) dn 0.0 h (tc:block-height o h))
      (if (= system "TRAY") (setq material (tc:name o))))
    (T (tc:fail "Chi chon MLINE hoac block thang dong.")))
  (if (or (<= (tc:dist a b) 0.000001) (<= width 0.0)) (tc:fail "Doan thang khong hop le."))
  (if (tc:pipe-p system) (tc:diameter system dn))
  (if (tc:xget o "VAT LIEU") (setq material (tc:xget o "VAT LIEU")))
  (if (tc:xget o "TC_HEIGHT") (setq h (atof (tc:xget o "TC_HEIGHT"))))
  (if (and (tc:xget o "TC_SYSTEM") (/= system (tc:xget o "TC_SYSTEM"))) (tc:fail "Hai he thong khong khop. Dung lenh dung he."))
  (list (cons 'obj o) (cons 'a a) (cons 'b b) (cons 'dn dn) (cons 'width width)
    (cons 'height h) (cons 'material material) (cons 'system system) (cons 'layer (vla-get-Layer o))))
(defun tc:s (seg key) (cdr (assoc key seg)))
(defun tc:endpoint-p (seg cp)
  (<= (min (tc:dist cp (tc:s seg 'a)) (tc:dist cp (tc:s seg 'b))) (tc:cfg 'gap)))
(defun tc:fit-pair (s1 s2 / a b c d cp ang end1 end2 kind rot name fit sys mat dn1 dn2 w1 w2 far1 far2 pairs best pair dist mirror)
  (setq a (tc:s s1 'a) b (tc:s s1 'b) c (tc:s s2 'a) d (tc:s s2 'b)
    sys (tc:s s1 'system) mat (tc:s s1 'material) dn1 (tc:s s1 'dn) dn2 (tc:s s2 'dn)
    w1 (tc:s s1 'width) w2 (tc:s s2 'width) mirror 1.0
    ang (* 180.0 (/ (tc:line-angle a b c d) pi)))
  (if (/= mat (tc:s s2 'material)) (tc:fail "Khong noi tu dong hai vat lieu khac nhau."))
  (if (< ang 0.1)
    (progn
      (if (equal w1 w2 0.01) (tc:fail "Hai doan song song cung kich thuoc: khong can reducer."))
      (if (< (tc:s s1 'width) (tc:s s2 'width)) (tc:fit-pair s2 s1)
        (progn
          (if (> (tc:dist c (tc:project c a b nil)) 0.1) (tc:fail "Reducer can hai doan dong truc."))
          (setq pairs (list (list a c) (list a d) (list b c) (list b d)) best (car pairs))
          (foreach pair (cdr pairs) (if (< (tc:dist (car pair) (cadr pair)) (tc:dist (car best) (cadr best))) (setq best pair)))
          (if (> (tc:dist (car best) (cadr best)) (tc:cfg 'gap)) (tc:fail "Khoang cach hai dau vuot sai so noi."))
          (setq cp (car best) far1 (tc:far-end cp a b) far2 (tc:far-end (cadr best) c d)
            rot (tc:angle far1 far2) kind "RED")
          (if (> (tc:dot (tc:v- far1 cp) (tc:v- far2 cp)) 0.0) (tc:fail "Hai doan reducer phai nam o hai phia nut noi."))
          (setq name (if (tc:pipe-p sys) (tc:branch-name sys mat kind dn1 dn2) (tc:trunk-fitting-name sys mat "RED")))
          (setq fit (tc:insert name cp rot (tc:s s1 'layer)))
          (tc:setup-fitting fit sys mat dn1 w1 w2 (tc:s s1 'height)) (list fit cp s1 s2))))
    (progn
      (if (not (or (< (abs (- ang 45.0)) 0.1) (< (abs (- ang 90.0)) 0.1))) (tc:fail "Chi ho tro nut 45/90 do."))
      (setq cp (tc:intersection a b c d))
      (if (or (null cp) (> (tc:dist cp (tc:project cp a b T)) (tc:cfg 'gap))
              (> (tc:dist cp (tc:project cp c d T)) (tc:cfg 'gap))) (tc:fail "Nut giao nam ngoai sai so noi."))
      (setq end1 (tc:endpoint-p s1 cp) end2 (tc:endpoint-p s2 cp)
        far1 (tc:far-end cp a b) far2 (tc:far-end cp c d))
      (cond
        ((and end1 end2)
          (if (not (equal w1 w2 0.01)) (tc:fail "Co can hai doan cung kich thuoc. Tao reducer rieng."))
          (setq kind "ELB" rot (tc:elbow-rotation far1 cp far2)
            name (tc:elbow-name sys mat dn1 (fix (+ ang 0.5)))))
        ((and (not end1) (not end2))
          (if (or (/= sys "TRAY") (< ang 89.9)) (tc:fail "Nut cross chi ho tro mang cap 90 do."))
          (setq kind "CROSS" rot (tc:angle a b) name (strcat "Cross " mat)))
        ((and end1 (not end2)) (setq name nil))
        (T
          (setq kind (if (> ang 89.9) "TEE" "Y"))
          (if (and (not (tc:pipe-p sys)) (= kind "Y")) (tc:fail "Mang/duct chu Y 45 do can chen phu kien thu cong."))
          (if (= kind "TEE") (setq rot (tc:angle cp far2))
            (progn
              (setq rot (tc:angle a b))
              (if (< (tc:dot (tc:v- far2 cp) (tc:v- b a)) 0.0) (setq rot (+ rot pi)))
              (if (> (tc:wrap (- (tc:angle cp far2) rot)) 0.0) (setq mirror -1.0))))
          (setq name (if (tc:pipe-p sys) (tc:branch-name sys mat kind dn1 dn2) (tc:trunk-fitting-name sys mat "TEE")))))
      (if (null name) (tc:fit-pair s2 s1)
        (progn
          (setq fit (tc:insert name cp rot (tc:s s1 'layer)))
          (if (< mirror 0.0) (vla-put-YScaleFactor fit mirror))
          (tc:setup-fitting fit sys mat dn1 w1 w2 (tc:s s1 'height)) (list fit cp s1 s2))))))
(defun tc:cut-interval (seg fit cp / a b len u x far p q overlap)
  (setq a (tc:s seg 'a) b (tc:s seg 'b) u (tc:unit (tc:v- b a)) len (tc:dist a b)
    x (tc:dot (tc:v- cp a) u) overlap (if (= (tc:s seg 'system) "UPVC") (tc:cfg 'overlap) 0.0))
  (cond
    ((<= x (tc:cfg 'gap)) (setq p 0.0 q (tc:dot (tc:v- (tc:port fit b overlap) a) u)))
    ((>= x (- len (tc:cfg 'gap))) (setq p (tc:dot (tc:v- (tc:port fit a overlap) a) u) q len))
    (T (setq p (tc:dot (tc:v- (tc:port fit a overlap) a) u)
             q (tc:dot (tc:v- (tc:port fit b overlap) a) u))))
  (if (or (< q p) (< q 0.0) (> p len)) (tc:fail "Fitting vuot khoi doan hoac sai huong cong noi."))
  (list p q))
(defun tc:trim-segments (plans / entries plan seg obj entry cuts iv spans span a b u len new previous)
  ;; Collect every cut against original coordinates, then split each source once.
  (foreach plan plans
    (foreach seg (list (nth 2 plan) (nth 3 plan))
      (setq obj (tc:s seg 'obj) entry (assoc (vla-get-Handle obj) entries)
        iv (tc:cut-interval seg (car plan) (cadr plan)))
      (if entry
        (foreach previous (caddr entry)
          (if (> (- (min (cadr iv) (cadr previous)) (max (car iv) (car previous))) 0.000001)
            (tc:fail "Hai fitting chong lan tren cung doan. Tang khoang cach nut noi."))))
      (if entry
        (setq entries (subst (list (car entry) seg (cons iv (caddr entry))) entry entries))
        (setq entries (cons (list (vla-get-Handle obj) seg (list iv)) entries)))))
  (foreach entry entries
    (setq seg (cadr entry) a (tc:s seg 'a) b (tc:s seg 'b) u (tc:unit (tc:v- b a)) len (tc:dist a b)
      spans (tc:complement (caddr entry) 0.0 len))
    (if (null spans) (tc:fail "Fitting chiem het doan. Tang khoang cach nut noi."))
    (foreach span spans
      (setq new (vla-Copy (tc:writable (tc:s seg 'obj)))) (tc:new new)
      (if (= (vla-get-ObjectName new) "AcDbMline")
        (vla-put-Coordinates new (tc:array (append (tc:v+ a (tc:v* u (car span))) (tc:v+ a (tc:v* u (cadr span)))) vlax-vbDouble))
        (progn (vla-put-InsertionPoint new (tc:3d (tc:v+ a (tc:v* u (car span)))))
          (tc:set-dyn new "Length" (- (cadr span) (car span)) T))))
    (tc:delete (tc:s seg 'obj))))
(defun tc:autofit (system / first branches second main seg plans obj mode plan)
  (tc:set 'system system)
  (setq first (tc:pick "\nChon doan chinh: " '("AcDbMline" "AcDbBlockReference")))
  (if first
    (progn (setq main (tc:segment first system)
      mode (tc:choose "\nChe do [Pair/Batch]" "Pair Batch" "Pair"))
      (if (= mode "Batch")
        (setq branches (tc:selection (if (tc:pipe-p system) '((0 . "MLINE")) '((0 . "INSERT")))))
        (if (setq second (tc:pick "\nChon doan thu hai: " '("AcDbMline" "AcDbBlockReference"))) (setq branches (list second))))
      (foreach obj branches
        (if (/= (vla-get-Handle first) (vla-get-Handle obj))
          (progn
            (setq seg (tc:segment obj system) plan (tc:fit-pair main seg))
            (tc:inherit-service (car plan) (tc:s (nth 2 plan) 'obj))
            (if (vl-some '(lambda (p) (< (tc:dist (cadr p) (cadr plan)) 0.1)) plans)
              (tc:fail "Nhieu nhanh trung nut. Tach xu ly nut Cross/phan nhanh, tranh hai fitting trung nhau."))
            (setq plans (cons plan plans)))))
      (if plans (progn (tc:trim-segments plans) (princ (strcat "\nDa noi " (itoa (length plans)) " nut.")))))))
(defun tc:manual-fitting ( / sys mat kind name dn d2 width fit pt rot)
  (setq sys (tc:cfg 'system) mat (tc:material sys) dn (tc:cfg 'dn) width (tc:cfg 'width))
  (if (tc:pipe-p sys) (tc:diameter sys dn))
  (setq kind (tc:choose "\nLoai [Elb90/Elb45/Tee/Y/Red/Cross/Name]" "Elb90 Elb45 Tee Y Red Cross Name" "Elb90"))
  (cond ((= kind "Name") (setq name (getstring T "\nTen block chinh xac: ")))
    ((member kind '("Elb90" "Elb45")) (setq name (tc:elbow-name sys mat dn (if (= kind "Elb45") 45 90))))
    (T (setq d2 (tc:positive "\nDuong kinh/rong nhanh" (if (tc:pipe-p sys) dn width)))
      (setq name (if (tc:pipe-p sys) (tc:branch-name sys mat (strcase kind) dn d2)
        (tc:trunk-fitting-name sys mat (strcase kind))))))
  (if (or (null name) (= name "")) (tc:fail "To hop phu kien/he thong chua duoc ho tro. Dung TCBLOCK de chon block cu the."))
  (if (setq pt (tc:point "\nDiem chen: "))
    (progn (setq rot (getangle (trans pt 0 1) "\nGoc xoay <0>: "))
      (setq rot (if rot (tc:angle pt (trans (polar (trans pt 0 1) rot 1.0) 1 0)) 0.0)
        fit (tc:insert name pt rot (tc:layer (tc:cfg 'layer) 3)))
      (tc:setup-fitting fit sys mat dn width (if d2 d2 width) (tc:cfg 'height)))))
(defun tc:upvc-rise (double / ml picked seg cp far rotation dn name fit fit2)
  (if (setq picked (entsel "\nPick gan dau MLINE UPVC: "))
    (progn (setq ml (tc:obj (car picked)) seg (tc:segment ml "UPVC") dn (tc:s seg 'dn)
      cp (tc:near-end (trans (cadr picked) 1 0) (tc:s seg 'a) (tc:s seg 'b))
      far (tc:far-end cp (tc:s seg 'a) (tc:s seg 'b)) rotation (+ (tc:angle cp far) pi)
      name (tc:elbow-name "UPVC" "UPVC" dn 45)
      fit (tc:insert name cp rotation (tc:s seg 'layer)))
      (tc:state fit (if double "UP90" "DN45") T)
      (tc:metadata fit "UPVC" "UPVC" dn 0.0 0.0)
      (if double
        (progn (setq fit2 (tc:insert name (tc:polar cp (tc:angle cp far) (* dn 2.0)) rotation (tc:s seg 'layer)))
          (tc:state fit2 "UP45" T) (tc:metadata fit2 "UPVC" "UPVC" dn 0.0 0.0))))))
(defun tc:split-duct ( / objs o seg maxlen len start new span u a)
  (setq maxlen (tc:positive "\nChieu dai moi doan ong gio" 1200.0) objs (tc:selection '((0 . "INSERT"))))
  (foreach o objs
    (setq seg (tc:segment o "DUCT") len (tc:dist (tc:s seg 'a) (tc:s seg 'b)) start 0.0
      u (tc:unit (tc:v- (tc:s seg 'b) (tc:s seg 'a))) a (tc:s seg 'a))
    (if (> len maxlen)
      (progn
        (while (< start (- len 0.000001))
          (setq span (min maxlen (- len start)) new (tc:new (vla-Copy (tc:writable o))))
          (vla-put-InsertionPoint new (tc:3d (tc:v+ a (tc:v* u start))))
          (tc:set-dyn new "Length" span T) (setq start (+ start span)))
        (tc:delete o)))))
(princ)

;;; ===== tc-blocks =====
;;; Block editing, placement and definition tools.
(defun tc:clone-at (source point / copy)
  (setq copy (tc:new (vla-Copy source)))
  (vla-Move copy (tc:3d (tc:insertion source)) (tc:3d point)) copy)
(defun tc:block-grid ( / sample a b cols rows mode dx dy nx ny pts p width height)
  (if (and (setq sample (tc:pick "\nBlock mau: " '("AcDbBlockReference")))
           (setq a (tc:point "\nGoc thu nhat vung bo tri: "))
           (setq b (tc:next-point a "\nGoc doi dien: ")))
    (progn
      (setq width (abs (- (car b) (car a))) height (abs (- (cadr b) (cadr a))))
      (if (or (< width 0.000001) (< height 0.000001)) (tc:fail "Vung bo tri phai co chieu rong va cao."))
      (setq mode (tc:choose "\nBo tri [Count/Spacing]" "Count Spacing" "Count"))
      (if (= mode "Count")
        (progn
          (setq cols (tc:integer "\nSo cot" 3) rows (tc:integer "\nSo hang" 2))
          (if (> (* (float cols) rows) 10000) (tc:fail "Gioi han 10000 block moi lenh."))
          (setq pts (tc:grid a b cols rows)))
        (progn
          (setq dx (tc:positive "\nKhoang cach cot" 2000.0) dy (tc:positive "\nKhoang cach hang" 2000.0)
            cols (max 1 (fix (/ width dx))) rows (max 1 (fix (/ height dy))) nx 0 pts nil)
          (if (> (* (float cols) rows) 10000) (tc:fail "Gioi han 10000 block moi lenh."))
          (repeat rows (setq ny 0)
            (repeat cols
              (setq p (list (+ (min (car a) (car b)) (/ (- width (* (1- cols) dx)) 2.0) (* ny dx))
                (+ (min (cadr a) (cadr b)) (/ (- height (* (1- rows) dy)) 2.0) (* nx dy)) 0.0)
                pts (cons p pts) ny (1+ ny))) (setq nx (1+ nx)))))
      (if (> (length pts) 10000) (tc:fail "Gioi han 10000 block moi lenh. Giam so hang/cot."))
      (foreach p pts (tc:clone-at sample p))
      (princ (strcat "\nDa bo tri " (itoa (length pts)) " block, giu dynamic va attributes cua mau.")))))
(defun tc:block-align ( / objs base a b axis origin mode spacing projections pair index anchor target)
  (setq objs (tc:selection '((0 . "INSERT"))))
  (if objs
    (progn
      (setq base (tc:pick "\nBlock neo (giu nguyen vi tri): " '("AcDbBlockReference"))
        origin (if base (tc:xy-check (tc:insertion base))))
      (if (and base (not (vl-some '(lambda (o) (= (vla-get-Handle o) (vla-get-Handle base))) objs)))
        (tc:fail "Block neo phai nam trong nhom da chon."))
      (if (and origin (setq a (tc:point "\nDiem thu nhat xac dinh huong truc: "))
               (setq b (tc:next-point a "\nDiem thu hai xac dinh huong truc: ")))
        (progn
          (setq axis (tc:unit (tc:v- b a))) (if (null axis) (tc:fail "Truc chuan co do dai bang 0."))
          (setq mode (tc:choose "\nCan hang [Project/Equal/Round]" "Project Equal Round" "Project"))
          (if (/= mode "Project") (setq spacing (tc:positive "\nKhoang cach / buoc lam tron" 100.0)))
          (foreach pair objs (setq projections (cons (cons (tc:dot (tc:v- (tc:insertion pair) origin) axis) pair) projections)))
          (setq projections (tc:sort projections '(lambda (x y) (< (car x) (car y)))) index 0 anchor 0)
          (foreach pair projections
            (if (= (vla-get-Handle (cdr pair)) (vla-get-Handle base)) (setq anchor index))
            (setq index (1+ index))) (setq index 0)
          (foreach pair projections
            (if (/= (vla-get-Handle (cdr pair)) (vla-get-Handle base))
              (progn
                (setq target (tc:v+ origin (tc:v* axis
                  (cond ((= mode "Equal") (* (- index anchor) spacing))
                        ((= mode "Round") (* spacing (tc:round-int (/ (car pair) spacing)))) (T (car pair))))))
                (vla-Move (tc:writable (cdr pair)) (tc:3d (tc:insertion (cdr pair))) (tc:3d target)) (tc:touch)))
            (setq index (1+ index))))))))
(defun tc:round-int (x) (if (< x 0.0) (- (fix (+ (- x) 0.5))) (fix (+ x 0.5))))
(defun tc:copy-dyn (source target / p key val)
  (foreach p (tc:dynprops source)
    (setq key (vla-get-PropertyName p) val (vlax-variant-value (vla-get-Value p)))
    (if (and (= (vla-get-ReadOnly p) :vlax-false) (not (null (tc:dyn target key))))
      (tc:set-dyn target key val nil))) target)
(defun tc:block-replace ( / sample objs source new mode oldname)
  (if (setq sample (tc:pick "\nChon block mau thay the: " '("AcDbBlockReference")))
    (progn
      (setq mode (tc:choose "\nPham vi [Selection/Name]" "Selection Name" "Selection"))
      (if (= mode "Name")
        (progn (setq source (tc:pick "\nChon block co ten can thay toan bo Model: " '("AcDbBlockReference")))
          (if source
            (progn (setq oldname (tc:name source))
              (vlax-for source (tc:space)
                (if (and (= (vla-get-ObjectName source) "AcDbBlockReference") (= (strcase (tc:name source)) (strcase oldname)))
                  (setq objs (cons source objs)))))))
        (setq objs (tc:selection '((0 . "INSERT")))))
      (foreach source objs
        (if (/= (vla-get-Handle source) (vla-get-Handle sample))
          (progn
            (tc:writable source) (setq new (tc:clone-at sample (tc:insertion source)))
            (vla-put-Layer new (vla-get-Layer source)) (vla-put-Rotation new (vla-get-Rotation source))
            (vla-put-XScaleFactor new (vla-get-XScaleFactor source))
            (vla-put-YScaleFactor new (vla-get-YScaleFactor source)) (vla-put-ZScaleFactor new (vla-get-ZScaleFactor source))
            (tc:copy-dyn source new) (tc:set-attributes new (tc:attributes source))
            (tc:copy-xdata source new) (tc:delete source)))))))
(defun tc:copy-xdata (source target / key val)
  (foreach key '("SYSTEM" "VAT LIEU" "TC_SYSTEM" "TC_DN" "TC_WIDTH" "TC_HEIGHT" "TC_ELEVATION" "TC_CABLE")
    (if (setq val (tc:xget source key)) (tc:xset target key val))))
(defun tc:block-rename ( / sample old name def)
  (if (setq sample (tc:pick "\nChon block can doi ten dinh nghia: " '("AcDbBlockReference")))
    (progn (setq old (tc:name sample) name (getstring T "\nTen moi: "))
      (if (or (= name "") (not (snvalid name)) (tc:block-present name)) (tc:fail "Ten moi khong hop le hoac da ton tai."))
      (setq def (vla-item (vla-get-Blocks (tc:doc)) old))
      (if (= (vla-get-IsXRef def) :vlax-true) (tc:fail "Khong doi ten Xref."))
      (vla-put-Name def name) (tc:touch)
      (princ "\nDa doi ten dinh nghia; tat ca tham chieu cung ten duoc cap nhat."))))
(defun tc:block-edit ( / o props p keys i key val old allowed)
  (if (setq o (tc:pick "\nChon dynamic block: " '("AcDbBlockReference")))
    (progn
      (setq props (tc:dynprops o) i 0)
      (foreach p props
        (if (= (vla-get-ReadOnly p) :vlax-false)
          (progn (setq keys (append keys (list (vla-get-PropertyName p))))
            (princ (strcat "\n" (itoa (setq i (1+ i))) ". " (vla-get-PropertyName p)
              " = " (vl-princ-to-string (vlax-variant-value (vla-get-Value p)))
              " | Allowed=" (vl-princ-to-string (tc:variant-list (vla-get-AllowedValues p))))))))
      (if (null keys) (tc:fail "Block khong co dynamic property co the sua."))
      (initget 6) (setq i (getint "\nSo thu tu property (Enter huy): "))
      (if i
        (progn (if (> i (length keys)) (tc:fail "So thu tu khong hop le."))
          (setq key (nth (1- i) keys) old (tc:dyn o key))
          (setq val (if (eq (type old) 'STR) (getstring T "\nGia tri moi (dung chinh xac AllowedValues): ") (getreal "\nGia tri moi: ")))
          (if val (tc:set-dyn (tc:writable o) key val T)))))))
(defun tc:attribute-edit ( / sample pairs pair val objs o tag)
  (if (setq sample (tc:pick "\nBlock mau de lay danh sach tag: " '("AcDbBlockReference")))
    (progn (setq pairs (tc:attributes sample))
      (foreach pair pairs (princ (strcat "\n" (car pair) " = " (cdr pair))))
      (setq tag (strcase (getstring T "\nTag can sua: ")))
      (if (not (assoc tag pairs)) (tc:fail "Tag khong co trong block mau."))
      (setq val (getstring T "\nNoi dung moi (co the rong): ") objs (tc:selection '((0 . "INSERT"))))
      (foreach o objs (tc:set-attributes (tc:writable o) (list (cons tag val)))))))
(defun tc:bounding-box ( / o children child low high p q lo hi pts saved)
  (if (setq o (tc:pick "\nBlock can ve khung trang thai hien thi: " '("AcDbBlockReference")))
    (progn (setq saved *tc-temps* children (tc:explode-temp o 0))
      (foreach child children
        (vla-GetBoundingBox child 'low 'high)
        (setq p (tc:variant-list low) q (tc:variant-list high)
          lo (if lo (mapcar 'min lo p) p) hi (if hi (mapcar 'max hi q) q)))
      (while (not (eq *tc-temps* saved)) (tc:temp-delete (car *tc-temps*)) (setq *tc-temps* (cdr *tc-temps*)))
      (if (null lo) (tc:fail "Block khong co hinh hoc co the ve khung."))
      (setq pts (list (list (car lo) (cadr lo) 0.0) (list (car hi) (cadr lo) 0.0)
        (list (car hi) (cadr hi) 0.0) (list (car lo) (cadr hi) 0.0)))
      (setq o (tc:polyline pts (tc:layer "TC_BOUNDINGBOX" 1))) (vla-put-Closed o :vlax-true))))
(defun tc:bylayer ( / objs o layer color nested seen)
  (setq layer (getstring T "\nLayer dich <TC_STANDARD>: ")) (if (= layer "") (setq layer "TC_STANDARD"))
  (setq color (tc:integer "\nMau layer ACI 1..255" 8))
  (if (> color 255) (tc:fail "ACI chi tu 1 den 255."))
  (tc:layer layer color) (vla-put-Color (vla-item (vla-get-Layers (tc:doc)) layer) color) (tc:touch)
  (setq nested (tc:choose "\nSua ben trong dinh nghia block (anh huong moi tham chieu) [Yes/No]" "Yes No" "No")
    objs (tc:selection nil))
  (foreach o objs (tc:standard-entity (tc:writable o) layer (= nested "Yes")))
  (vla-Regen (tc:doc) 1))
(defun tc:standard-entity (o layer recursive / name def child prop)
  (tc:put-layer o layer) (tc:touch)
  (foreach prop '(TextColor DimensionLineColor ExtensionLineColor)
    (if (vlax-property-available-p o prop T) (vlax-put-property o prop 256)))
  (if (and recursive (= (vla-get-ObjectName o) "AcDbBlockReference"))
    (progn (setq name (vla-get-Name o) def (vla-item (vla-get-Blocks (tc:doc)) name))
      (if (and (not (member name seen)) (= (vla-get-IsXRef def) :vlax-false))
        (progn (setq seen (cons name seen)) (vlax-for child def (tc:standard-entity child "0" T)))))))
(defun tc:insert-aligned ( / sample name pt tangent hit curve close param deriv angle obj)
  (if (setq sample (tc:pick "\nBlock mau: " '("AcDbBlockReference")))
    (progn
      (setq hit (entsel "\nPick LINE/POLYLINE/ARC tai vi tri chen: "))
      (if hit
        (progn (setq curve (car hit) pt (trans (cadr hit) 1 0)
          close (vl-catch-all-apply 'vlax-curve-getClosestPointTo (list curve pt)))
          (if (vl-catch-all-error-p close) (tc:fail "Doi tuong khong phai duong cong ho tro."))
          (tc:xy-check close)
          (setq param (vlax-curve-getParamAtPoint curve close) deriv (vlax-curve-getFirstDeriv curve param)
            angle (atan (cadr deriv) (car deriv)) obj (tc:clone-at sample close))
          (vla-put-Rotation obj angle))))))
(defun tc:line-to-tray ( / lines line segs seg base u n angle tol maxgap minp maxp minx maxx item a b len center groups group found)
  ;; Pair/group only overlapping parallel lines; source entities are retained by default.
  (setq lines (tc:selection '((0 . "LINE"))) maxgap (tc:positive "\nBe rong nhom toi da" 1000.0))
  (foreach line lines
    (setq a (tc:xy-check (tc:variant-list (vla-get-StartPoint line))) b (tc:xy-check (tc:variant-list (vla-get-EndPoint line))))
    (if (> (tc:dist a b) 0.000001) (setq segs (cons (list line a b) segs))))
  (while segs
    (setq base (car segs) segs (cdr segs) a (cadr base) b (caddr base) u (tc:unit (tc:v- b a)) n (tc:perp u)
      group (list base) minx 0.0 maxx (tc:dist a b) minp 0.0 maxp 0.0)
    (foreach seg segs
      (if (and (< (tc:line-angle a b (cadr seg) (caddr seg)) (/ pi 180.0))
               (<= (abs (tc:dot (tc:v- (cadr seg) a) n)) maxgap)
               (> (min maxx (max (tc:dot (tc:v- (cadr seg) a) u) (tc:dot (tc:v- (caddr seg) a) u)))
                  (max minx (min (tc:dot (tc:v- (cadr seg) a) u) (tc:dot (tc:v- (caddr seg) a) u)))))
        (setq group (cons seg group))))
    (foreach seg group (setq segs (tc:remove-one seg segs)))
    (if (> (length group) 1)
      (progn
        (foreach seg group
          (foreach item (list (cadr seg) (caddr seg))
            (setq minp (min minp (tc:dot (tc:v- item a) n)) maxp (max maxp (tc:dot (tc:v- item a) n))
              minx (max minx (min (tc:dot (tc:v- (cadr seg) a) u) (tc:dot (tc:v- (caddr seg) a) u)))
              maxx (min maxx (max (tc:dot (tc:v- (cadr seg) a) u) (tc:dot (tc:v- (caddr seg) a) u))))))
        (if (> (- maxp minp) 0.01)
          (progn (setq center (tc:v+ a (tc:v+ (tc:v* n (/ (+ minp maxp) 2.0)) (tc:v* u minx))))
            (tc:straight center (tc:v+ center (tc:v* u (- maxx minx))) "TRAY" "Cable tray" 0.0 (- maxp minp)
              (tc:cfg 'height) (tc:layer (tc:cfg 'layer) 3))
            (if (= (tc:cfg 'erase) "1") (foreach seg group (tc:delete (tc:writable (car seg)))))))))))
(princ)

;;; ===== tc-electrical =====
;;; Electrical routing between selected insertion points.
(defun tc:electrical-points ( / objs obj base pts start)
  (setq objs (tc:selection '((0 . "INSERT"))))
  (if (< (length objs) 2) (tc:fail "Can it nhat hai block."))
  (setq base (tc:pick "\nChon block dau trong nhom: " '("AcDbBlockReference")))
  (if (null base) (tc:fail "Chua chon block dau."))
  (if (not (vl-some '(lambda (o) (= (vla-get-Handle o) (vla-get-Handle base))) objs))
    (tc:fail "Block dau phai thuoc nhom da chon."))
  (setq start (tc:xy-check (tc:insertion base)))
  (foreach obj objs (setq pts (cons (tc:xy-check (tc:insertion obj)) pts)))
  (list start (tc:remove-one start (reverse pts))))
(defun tc:fillet-poly (o radius)
  (if (> radius 0.0)
    (progn (setvar "FILLETRAD" radius) (setvar "OSMODE" 0)
      (command-s "_.FILLET" "_Polyline" (tc:ename o)) (tc:touch))) o)
(defun tc:electrical (mode / data start pts route o i a b c box props prop options state rotation h)
  (setq data (tc:electrical-points) start (car data) pts (cadr data))
  (if (member mode '("ZIGZAG" "BOX" "ARC"))
    (progn (setq route (tc:row-order (cons start pts) (tc:cfg 'rowtol)))
      (if (> (tc:dist start (car route)) (tc:dist start (last route))) (setq route (reverse route)))
      ;; Rotate a snake to the selected start without dropping any points.
      (while (not (equal (car route) start 0.000001)) (setq route (append (cdr route) (list (car route))))))
    (setq route (tc:nearest-order pts start)))
  (if (= mode "GRID") (setq route (tc:ortho-route route)))
  (setq route (tc:dedup route))
  (if (< (length route) 2) (tc:fail "Cac block trung diem chen."))
  (setq o (tc:polyline route (tc:layer (tc:cfg 'layer) 2)))
  (cond
    ((= mode "ARC")
      (setq h (tc:positive "\nDo vong cung" (tc:cfg 'drop)) i 0)
      (repeat (1- (length route))
        ;; Exact sagitta/chord relation; avoids division by (r-h) singularities.
        (vla-SetBulge o i (/ (* 2.0 h) (tc:dist (nth i route) (nth (1+ i) route)))) (setq i (1+ i))))
    ((= mode "FILLET") (tc:fillet-poly o (tc:cfg 'fillet)))
    ((= mode "BOX")
      (tc:ensure-block "HopchiangD20V1")
      (setq i 0)
      (foreach b route
        (setq a (if (> i 0) (nth (1- i) route)) c (nth (1+ i) route)
          rotation (cond (c (tc:angle b c)) (a (tc:angle a b)) (T 0.0))
          box (tc:insert "HopchiangD20V1" b rotation (tc:cfg 'layer)))
        (vla-put-XScaleFactor box 2.0) (vla-put-YScaleFactor box 2.0) (vla-put-ZScaleFactor box 2.0)
        (setq options nil)
        (foreach prop (tc:dynprops box)
          (if (= (strcase (vla-get-PropertyName prop)) "OPTIONS") (setq options (tc:variant-list (vla-get-AllowedValues prop)))))
        (setq state (if (and a c (> (abs (tc:turn a b c)) 0.1)) 2 1))
        (if (<= (length options) state) (tc:fail "HopchiangD20V1 thieu AllowedValues cua Options."))
        (setq state (nth state options)) (if (eq (type state) 'VARIANT) (setq state (vlax-variant-value state)))
        (tc:set-dyn box "Options" state T) (setq i (1+ i)))))
  (tc:xset o "TC_CABLE" "CABLE") (tc:xset o "SYSTEM" (tc:cfg 'service))
  (princ (strcat "\nDa noi " (itoa (length route)) " diem.")))
(defun tc:offset-links (spine-only / objs obj pts center p guide u axis sorted a b pa pb o)
  (setq objs (tc:selection '((0 . "INSERT"))))
  (if (< (length objs) 2) (tc:fail "Can it nhat hai block."))
  (foreach obj objs (setq pts (cons (tc:xy-check (tc:insertion obj)) pts)))
  (setq center (tc:v* (apply 'mapcar (cons '+ pts)) (/ 1.0 (length pts))))
  (if (setq guide (tc:next-point center "\nDiem tren truc day chinh: "))
    (progn
      (setq u (tc:unit (tc:v- guide center))) (if (null u) (tc:fail "Diem truc trung tam nhom."))
      (setq axis (tc:perp u) sorted (tc:sort pts '(lambda (a b) (< (tc:dot a axis) (tc:dot b axis)))))
      (if spine-only
        (progn
          (foreach p sorted
            (setq pa (tc:v+ guide (tc:v* axis (tc:dot (tc:v- p guide) axis))))
            (if (> (tc:dist p pa) 0.000001) (tc:polyline (list p pa) (tc:layer (tc:cfg 'layer) 2))))
          (setq a (car sorted) b (last sorted))
          (tc:polyline (list (tc:v+ guide (tc:v* axis (tc:dot (tc:v- a guide) axis)))
                            (tc:v+ guide (tc:v* axis (tc:dot (tc:v- b guide) axis)))) (tc:cfg 'layer)))
        (progn
          (setq a (car sorted))
          (foreach b (cdr sorted)
            (setq pa (tc:v+ guide (tc:v* axis (tc:dot (tc:v- a guide) axis)))
                  pb (tc:v+ guide (tc:v* axis (tc:dot (tc:v- b guide) axis)))
                  o (tc:polyline (list a pa pb b) (tc:layer (tc:cfg 'layer) 2)))
            (tc:fillet-poly o (tc:cfg 'fillet)) (tc:xset o "TC_CABLE" "CABLE") (setq a b)))))))
(defun tc:path-between (curve start end / d1 d2 pts point param i result)
  ;; Preserve every original vertex between two projections. Curves must be straight-segment polylines.
  (setq pts (tc:poly-points curve) d1 (vlax-curve-getDistAtPoint curve start) d2 (vlax-curve-getDistAtPoint curve end))
  (if (> d1 d2) (reverse (tc:path-between curve end start))
    (progn
      (setq result (list start))
      (foreach point pts
        (setq param (vlax-curve-getDistAtPoint curve point))
        (if (and (> param (+ d1 0.000001)) (< param (- d2 0.000001))) (setq result (append result (list point)))))
      (tc:dedup (append result (list end))))))
(defun tc:panel-route ( / panel main objs obj root projection p branch path route o)
  (if (and (setq panel (tc:pick "\nBlock tu dien nguon: " '("AcDbBlockReference")))
           (setq main (tc:pick "\nPolyline truc cap chinh (giu nguyen): " '("AcDbPolyline"))))
    (progn
      (tc:poly-points main) (setq root (tc:xy-check (tc:insertion panel))
        projection (vlax-curve-getClosestPointTo main root) objs (tc:selection '((0 . "INSERT"))))
      (foreach obj objs
        (if (/= (vla-get-Handle obj) (vla-get-Handle panel))
          (progn
            (setq p (tc:xy-check (tc:insertion obj)) branch (vlax-curve-getClosestPointTo main p)
              path (tc:path-between main projection branch)
              route (tc:dedup (append (list root (list (car projection) (cadr root) 0.0)) path
                (list (list (car p) (cadr branch) 0.0) p)))
              o (tc:polyline route (tc:layer (tc:cfg 'layer) 2)))
            (tc:xset o "TC_CABLE" (strcat (tc:name panel) " -> " (tc:name obj)))
            (tc:xset o "SYSTEM" (tc:cfg 'service))))))))
(princ)

;;; ===== tc-report =====
;;; Quantity extraction, CAD tables and Excel-compatible CSV.
(defun tc:curve-length (o / value)
  (setq value (vl-catch-all-apply 'vlax-curve-getDistAtParam (list o
    (vl-catch-all-apply 'vlax-curve-getEndParam (list o)))))
  (if (vl-catch-all-error-p value) 0.0 value))
(defun tc:mline-length (o / pts sum)
  (setq pts (tc:chunks (tc:variant-list (vla-get-Coordinates o)) 3) sum 0.0)
  (while (cdr pts) (setq sum (+ sum (tc:dist (car pts) (cadr pts))) pts (cdr pts))) sum)
(defun tc:entity-system (o / val mat name)
  (if (setq val (tc:xget o "TC_SYSTEM")) val
    (progn
      (setq mat (tc:xget o "VAT LIEU"))
      (cond
        ((and mat (wcmatch (strcase mat) "*PPR*")) "PPR")
        ((and mat (wcmatch (strcase mat) "*UPVC*")) "UPVC")
        ((and mat (wcmatch (strcase mat) "*STK*,*STEEL*")) "STEEL")
        ((= (vla-get-ObjectName o) "AcDbBlockReference")
          (setq name (strcase (tc:name o)))
          (cond ((wcmatch name "* PPR") "PPR") ((wcmatch name "SCREW-*,WELD-*") "STEEL")
            ((wcmatch name "*TRUNKING*,*CABLE TRAY*,*LADDER*") "TRAY")
            ((wcmatch name "ONG GIO*,CO *,CON *,TE *,CHAC *") "DUCT")
            ((wcmatch name "ELB*-D*,TEE-D*,RED-D*,Y-D*") "UPVC") (T "BLOCK")))
        ((tc:xget o "TC_CABLE") "CABLE") (T "UNCLASSIFIED")))))
(defun tc:description (o / typ name atts pair p label)
  (setq typ (vla-get-ObjectName o))
  (cond
    ((= typ "AcDbBlockReference")
      (setq label (tc:name o) atts (acad_strlsort (mapcar '(lambda (pair) (strcat (car pair) "=" (cdr pair))) (tc:attributes o))))
      (foreach name atts (setq label (strcat label " | " name)))
      ;; Include evaluated size and visibility to avoid combining distinct fittings.
      (foreach name '("Width1" "Width2" "Diameter" "Diameter1" "Diameter2" "DN" "Visibility" "Visibility1" "Options")
        (if (setq p (tc:dyn o name)) (setq label (strcat label " | " name "=" (vl-princ-to-string p))))) label)
    ((= typ "AcDbMline") (strcat "ONG MLINE D" (rtos (abs (vla-get-MLineScale o)) 2 3)))
    ((tc:xget o "TC_CABLE") (tc:xget o "TC_CABLE"))
    (T typ)))
(defun tc:straight-block-p (name)
  (member (strcase name) '("TRUNKING" "CABLE TRAY" "LADDER" "ONG GIO NEP TDC" "ONG GIO NEP C"
    "ONG GIO TRON" "ONG GIO TIEU AM NEP TDC" "ONG GIO CACH NHIET NEP TDC" "ONG GIO CACH NHIET NEP C")))
(defun tc:entity-length (o / typ length)
  (setq typ (vla-get-ObjectName o))
  (cond ((= typ "AcDbMline") (tc:mline-length o))
    ((= typ "AcDbBlockReference")
      (if (and (tc:straight-block-p (tc:name o)) (setq length (tc:dyn o "Length")))
        (* length (abs (vla-get-XScaleFactor o))) 0.0))
    (T (tc:curve-length o))))
(defun tc:quantity (filter cable / objs o typ sys desc material service layer key pair row len out)
  (setq objs (tc:selection (if cable '((0 . "LWPOLYLINE,POLYLINE,LINE,ARC")) '((0 . "INSERT,MLINE,LWPOLYLINE,POLYLINE,LINE,ARC")))))
  (foreach o objs
    (setq typ (vla-get-ObjectName o) sys (tc:entity-system o))
    (if (or (null filter) (= sys filter))
      (progn
        (setq desc (tc:description o) material (tc:xget o "VAT LIEU") service (tc:xget o "SYSTEM") layer (vla-get-Layer o)
          material (if material material "") service (if service service "")
          len (+ (tc:entity-length o) (if cable (tc:cfg 'allowance) 0.0))
          key (list desc material service layer sys) pair (assoc key out))
        (if pair (setq out (subst (list key (1+ (cadr pair)) (+ (caddr pair) len)) pair out))
          (setq out (cons (list key 1 len) out))))))
  (if (null out) (tc:fail "Khong co doi tuong phu hop de thong ke."))
  (setq out (tc:sort out '(lambda (a b) (< (strcase (caar a)) (strcase (caar b))))) row 0)
  (mapcar '(lambda (pair) (setq row (1+ row))
    (list (itoa row) (caar pair) (itoa (cadr pair)) (rtos (/ (caddr pair) (tc:cfg 'unit)) 2 3)
      (cadar pair) (nth 2 (car pair)) (nth 3 (car pair)) (nth 4 (car pair)))) out))
(defun tc:table (title headers rows / point table n r c row value)
  (if (setq point (tc:point "\nDiem dat bang thong ke: "))
    (progn
      (setq n (length headers) table (tc:new (vla-AddTable (tc:space) (tc:3d point) (+ (length rows) 2) n
        (* 2.5 (tc:cfg 'text)) (* 14.0 (tc:cfg 'text)))))
      (vla-put-RegenerateTableSuppressed table :vlax-true)
      (vla-SetTextHeight table 7 (tc:cfg 'text))
      (vla-SetText table 0 0 title) (vla-MergeCells table 0 0 0 (1- n))
      (setq c 0) (foreach value headers (vla-SetText table 1 c value) (setq c (1+ c)))
      (setq r 2)
      (foreach row rows (setq c 0)
        (foreach value row (vla-SetText table r c value) (setq c (1+ c))) (setq r (1+ r)))
      (vla-SetColumnWidth table 0 (* 4.0 (tc:cfg 'text)))
      (vla-SetColumnWidth table 1 (* 55.0 (tc:cfg 'text)))
      (vla-put-RegenerateTableSuppressed table :vlax-false) (vla-Update table) table)))
(defun tc:csv-cell (s / i c out)
  (setq i 1 out "\"")
  ;; Keep spreadsheet formula-like text inert in the exported file.
  (if (and (> (strlen s) 0) (member (substr s 1 1) '("=" "+" "-" "@"))) (setq s (strcat "'" s)))
  (while (<= i (strlen s))
    (setq c (substr s i 1) out (strcat out (if (= c "\"") "\"\"" c)) i (1+ i))) (strcat out "\""))
(defun tc:join (xs separator / out s)
  (if xs (progn (setq out (car xs)) (foreach s (cdr xs) (setq out (strcat out separator s)))))
  (if out out ""))
(defun tc:csv (headers rows / path stream result row)
  (if (setq path (getfiled "Luu CSV (mo bang Excel)" (strcat (getvar "DWGPREFIX") "ToolsCad.csv") "csv" 1))
    (progn
      (setq stream (open path "w" "utf8-bom"))
      (if (null stream) (tc:fail "Khong ghi duoc CSV. Kiem tra quyen ghi va Excel dang mo file."))
      (setq result (vl-catch-all-apply '(lambda ()
        (write-line (tc:join (mapcar 'tc:csv-cell headers) ",") stream)
        (foreach row rows (write-line (tc:join (mapcar 'tc:csv-cell row) ",") stream))) nil))
      (close stream)
      (if (vl-catch-all-error-p result) (tc:fail (strcat "Ghi CSV loi: " (vl-catch-all-error-message result))))
      (princ (strcat "\nDa xuat CSV: " path)))))
(defun tc:statistics (filter cable / rows headers mode)
  (setq rows (tc:quantity filter cable) headers '("STT" "MO TA" "SO LUONG" "TONG DAI (m)" "VAT LIEU" "HE THONG" "LAYER" "NHOM")
    *tc-last-report* (list headers rows)
    mode (tc:choose "\nKet qua [Table/CSV/Both]" "Table CSV Both" "Table"))
  (if (member mode '("Table" "Both")) (tc:table "BANG THONG KE TOOLS CAD" headers rows))
  (if (member mode '("CSV" "Both")) (tc:csv headers rows)))
(defun tc:export-tables ( / objs o rows headers r c row)
  (setq objs (tc:selection '((0 . "ACAD_TABLE"))))
  (foreach o objs
    (setq r 0)
    (repeat (vla-get-Rows o) (setq row nil c 0)
      (repeat (vla-get-Columns o) (setq row (cons (vla-GetText o r c) row) c (1+ c)))
      (setq rows (append rows (list (reverse row))) r (1+ r)))
    (setq rows (append rows (list (list "")))))
  (if rows (tc:csv (car rows) (cdr rows))))
(defun tc:dimension-total ( / objs o rows total value i)
  (setq objs (tc:selection '((0 . "DIMENSION"))) total 0.0 i 0)
  (foreach o objs
    ;; Only linear dimensions have length units; angular/radial dimensions are excluded.
    (if (member (vla-get-ObjectName o) '("AcDbAlignedDimension" "AcDbRotatedDimension"))
      (progn (setq value (vla-get-Measurement o) total (+ total value) i (1+ i))
        (setq rows (cons (list (itoa i) (vla-get-Handle o) (rtos value 2 3) (vla-get-Layer o)) rows)))))
  (if rows
    (tc:table "TONG DIM (DON VI BAN VE)" '("STT" "HANDLE" "CHIEU DAI" "LAYER")
      (append (reverse rows) (list (list "" "TONG" (rtos total 2 3) ""))))
    (tc:fail "Khong co DIM thang de cong.")))
(princ)

;;; ===== tc-annotate =====
;;; Dimensions, notes and XData utilities.
(defun tc:aligned-dim (a b point layer / o)
  (if (> (tc:dist a b) 0.000001)
    (progn (setq o (tc:new (vla-AddDimAligned (tc:space) (tc:3d a) (tc:3d b) (tc:3d point))))
      (tc:put-layer o layer) o)))
(defun tc:dim-blocks ( / objs a b axis points origin location pair mode o first prev)
  (setq objs (tc:selection '((0 . "INSERT"))))
  (if (and (> (length objs) 1) (setq a (tc:point "\nDiem dau truc DIM: "))
    (setq b (tc:next-point a "\nDiem cuoi truc DIM: ")))
    (progn
      (setq axis (tc:unit (tc:v- b a))) (if (null axis) (tc:fail "Truc DIM bang 0."))
      (if (setq location (tc:point "\nVi tri duong DIM: "))
        (progn
          (foreach o objs (setq points (cons (tc:xy-check (tc:insertion o)) points)))
          (setq points (tc:sort points '(lambda (x y) (< (tc:dot x axis) (tc:dot y axis))))
            prev (car points) first prev)
          (foreach pair (cdr points)
            (if (> (abs (tc:dot (tc:v- pair prev) axis)) 0.000001)
              (progn (setq o (tc:new (vla-AddDimRotated (tc:space) (tc:3d prev) (tc:3d pair)
                (tc:3d location) (tc:angle a b)))) (tc:put-layer o (tc:layer "TC_DIM" 7))))
            (setq prev pair))
          (if (= (tc:choose "\nThem DIM tong [Yes/No]" "Yes No" "Yes") "Yes")
            (progn (setq location (tc:v+ location (tc:v* (tc:perp axis) (* 3.0 (tc:cfg 'text))))
              o (tc:new (vla-AddDimRotated (tc:space) (tc:3d first) (tc:3d prev) (tc:3d location) (tc:angle a b))))
              (tc:put-layer o "TC_DIM"))))))))
(defun tc:dim-segments ( / objs o pts a b distance offset location sys)
  (setq distance (tc:positive "\nKhoang cach DIM" 500.0)
    objs (tc:selection '((0 . "LWPOLYLINE,MLINE,INSERT,LINE"))))
  (foreach o objs
    (setq pts
      (cond ((= (vla-get-ObjectName o) "AcDbPolyline") (tc:poly-points o))
        ((= (vla-get-ObjectName o) "AcDbMline") (tc:chunks (tc:variant-list (vla-get-Coordinates o)) 3))
        ((= (vla-get-ObjectName o) "AcDbLine") (list (tc:variant-list (vla-get-StartPoint o)) (tc:variant-list (vla-get-EndPoint o))))
        (T (setq sys (tc:entity-system o))
          (if (not (member sys '("TRAY" "DUCT"))) (tc:fail "Chi DIM block thang mang/ong gio."))
          (setq sys (tc:segment o sys)) (list (tc:s sys 'a) (tc:s sys 'b)))))
    (while (cdr pts)
      (setq a (tc:xy-check (car pts)) b (tc:xy-check (cadr pts))
        location (tc:polar (tc:v* (tc:v+ a b) 0.5) (+ (tc:angle a b) (/ pi 2.0)) distance))
      (tc:aligned-dim a b location (tc:layer "TC_DIM" 7)) (setq pts (cdr pts)))))
(defun tc:curve-text ( / o text height offset curve middle param tangent angle point obj)
  (if (setq o (tc:pick "\nChon duong cong de dat text: " nil))
    (progn (setq curve (tc:ename o) middle (/ (tc:curve-length o) 2.0))
      (if (<= middle 0.0) (tc:fail "Doi tuong khong co chieu dai duong cong."))
      (setq text (getstring T "\nNoi dung text: ") height (tc:positive "\nChieu cao chu" (tc:cfg 'text))
        offset (tc:positive "\nKhoang cach text toi tuyen" (* height 1.5))
        point (tc:xy-check (vlax-curve-getPointAtDist curve middle)) param (vlax-curve-getParamAtPoint curve point)
        tangent (vlax-curve-getFirstDeriv curve param) angle (atan (cadr tangent) (car tangent)))
      (setq point (tc:polar point (+ angle (/ pi 2.0)) offset))
      (if (or (> angle (/ pi 2.0)) (< angle (- (/ pi 2.0)))) (setq angle (+ angle pi)))
      (setq obj (tc:new (vla-AddText (tc:space) text (tc:3d point) height)))
      (vla-put-Rotation obj angle) (tc:put-layer obj (tc:layer (tc:cfg 'layer) 7)))))
(defun tc:leader ( / a b text obj)
  (if (and (setq a (tc:point "\nDau mui ten: ")) (setq b (tc:next-point a "\nVi tri ghi chu: ")))
    (progn (setq text (getstring T "\nNoi dung ghi chu: ")
      obj (tc:new (vla-AddMLeader (tc:space) (tc:array (append a b) vlax-vbDouble) 0)))
      (vla-put-ContentType obj 2) (vla-put-TextString obj text)
      (vla-put-TextHeight obj (tc:cfg 'text)) (tc:put-layer obj (tc:layer (tc:cfg 'layer) 7)))))
(defun tc:xdata-edit (write / objs obj key value)
  (setq key (getstring T "\nTen nhom XData <SYSTEM>: ")) (if (= key "") (setq key "SYSTEM"))
  (if (not (snvalid key)) (tc:fail "Ten XData khong hop le."))
  (if write (setq value (getstring T "\nNoi dung: ")))
  (setq objs (tc:selection nil))
  (foreach obj objs
    (if write (tc:xset (tc:writable obj) key value)
      (princ (strcat "\n" (vla-get-Handle obj) " | " key " = " (if (tc:xget obj key) (tc:xget obj key) "<chua gan>"))))))
(defun tc:iso ( / objs base angle block source array ref exploded obj)
  (setq objs (tc:selection nil))
  (if (and objs (setq base (tc:point "\nDiem goc 2.5D (giu ban goc): ")))
    (progn
      (setq angle (tc:choose "\nGoc [A30/A45]" "A30 A45" "A30")
        block (tc:new (vla-Add (vla-get-Blocks (tc:doc)) (tc:3d base) "*U")))
      (vla-CopyObjects (tc:doc) (tc:array objs vlax-vbObject) block)
      ;; Match test.bas's nonuniform block scaling, retaining original entities.
      (setq ref (tc:new (vla-InsertBlock (tc:space) (tc:3d base) (vla-get-Name block) 1.0 0.577350269 1.0
        (* pi (/ (if (= angle "A45") 45.0 30.0) 180.0)))))
      (setq exploded (vlax-invoke ref 'Explode))
      (foreach obj exploded (tc:new obj)) (tc:delete ref)
      (princ "\nDa tao ban sao 2.5D theo quy tac VBA, ban goc duoc giu nguyen."))))
(princ)

;;; ===== tc-drain =====
;;; Planar drainage: chamfer vertices and attach branch endpoints to a main route.
(defun tc:chamfer-points (pts amount / out i a b c pre post d)
  (if (< (length pts) 3) pts
    (progn
      (setq i 1 out (list (car pts)))
      (while (< i (1- (length pts)))
        (setq a (nth (1- i) pts) b (nth i pts) c (nth (1+ i) pts))
        (if (equal (tc:corner a b c) 90)
          (progn (setq d (min amount (* 0.4 (tc:dist a b)) (* 0.4 (tc:dist b c)))
            pre (tc:polar b (tc:angle b a) d) post (tc:polar b (tc:angle b c) d)
            out (append out (list pre post))))
          (setq out (append out (list b))))
        (setq i (1+ i))) (append out (list (last pts))))))
(defun tc:chamfer ( / objs o pts new amount)
  (setq amount (tc:positive "\nKhoang vat goc 45" 100.0) objs (tc:selection '((0 . "LWPOLYLINE"))))
  (foreach o objs
    (setq pts (tc:poly-points o) new (tc:new (vla-Copy (tc:writable o))))
    (vla-put-Coordinates new (tc:array (apply 'append (mapcar '(lambda (p) (list (car p) (cadr p)))
      (tc:chamfer-points pts amount))) vlax-vbDouble))
    (if (= (tc:cfg 'erase) "1") (tc:delete o))))
(defun tc:insert-node (pts node / out a b found)
  (setq a (car pts) out (list a))
  (foreach b (cdr pts)
    (if (and (not found) (tc:on-segment node a b 0.01))
      (progn (if (and (> (tc:dist node a) 0.000001) (> (tc:dist node b) 0.000001))
        (setq out (append out (list node)))) (setq found T)))
    (setq out (append out (list b)) a b)) out)
(defun tc:drain-connect ( / main root rootproj rootdist branches o pts mainpts a b pa pb near far cp distmain targetdist join branchcut distance len new nodes)
  (if (and (setq main (tc:pick "\nChon polyline ong thoat chinh: " '("AcDbPolyline")))
           (setq root (tc:point "\nDiem huong ve ong dung/xa cuoi tuyen: ")))
    (progn
      (setq mainpts (tc:poly-points main) rootproj (vlax-curve-getClosestPointTo main root)
        rootdist (vlax-curve-getDistAtPoint main rootproj) len (tc:curve-length main)
        distance (tc:positive "\nKhoang vat nhanh 45 do" 100.0) branches (tc:selection '((0 . "LWPOLYLINE"))))
      (foreach o branches
        (if (/= (vla-get-Handle o) (vla-get-Handle main))
          (progn
            (setq pts (tc:poly-points o) a (car pts) b (last pts)
              pa (vlax-curve-getClosestPointTo main a) pb (vlax-curve-getClosestPointTo main b))
            (if (< (tc:dist a pa) (tc:dist b pb))
              (setq pts (reverse pts) near a cp pa) (setq near b cp pb))
            (if (> (tc:dist near cp) (tc:cfg 'gap)) (tc:fail "Dau nhanh cach ong chinh qua sai so noi."))
            (setq far (nth (- (length pts) 2) pts) distmain (vlax-curve-getDistAtPoint main cp)
              targetdist (max 0.0 (min len (+ distmain (if (> rootdist distmain) distance (- distance)))))
              join (vlax-curve-getPointAtDist main targetdist)
              branchcut (tc:polar cp (tc:angle cp far) (min distance (* 0.4 (tc:dist cp far)))))
            (if (not (equal (abs (tc:dot (tc:unit (tc:v- far cp)) (tc:unit (tc:v- join cp)))) 0.0 0.001))
              (tc:fail "Nhanh phai vuong goc doan chinh va cach dinh chinh it nhat khoang vat."))
            ;; Equal legs give a genuine 45-degree diagonal.
            (setq branchcut (tc:polar cp (tc:angle cp far) (tc:dist cp join))
              new (tc:new (vla-Copy (tc:writable o))))
            (if (>= (tc:dist cp join) (* 0.8 (tc:dist cp far))) (tc:fail "Doan nhanh qua ngan de vat goc."))
            (setq pts (append (reverse (cdr (reverse pts))) (list branchcut join)))
            (vla-put-Coordinates new (tc:array (apply 'append (mapcar '(lambda (p) (list (car p) (cadr p)))
              (tc:dedup pts))) vlax-vbDouble))
            (setq nodes (cons join nodes))
            (if (= (tc:cfg 'erase) "1") (tc:delete o)))))
      (if nodes
        (progn
          (setq new (tc:new (vla-Copy (tc:writable main))))
          (foreach join nodes (setq mainpts (tc:insert-node mainpts join)))
          (vla-put-Coordinates new (tc:array (apply 'append (mapcar '(lambda (p) (list (car p) (cadr p))) mainpts)) vlax-vbDouble))
          (if (= (tc:cfg 'erase) "1") (tc:delete main)))))))
(princ)

;;; ===== tc-ui =====
;;; DCL is embedded in the release LSP and written to a unique temporary file.
(setq *tc-systems* '("PPR" "UPVC" "STEEL" "TRAY" "DUCT"))
(setq *tc-groups* '("Ve ong / mang / duct" "Noi phu kien" "Block / thu vien" "Dien / day cap" "DIM / ghi chu" "Thong ke / CSV" "Tien ich / kiem tra"))
(defun tc:materials (sys)
  (cond ((= sys "PPR") '("PPR")) ((= sys "UPVC") '("UPVC")) ((= sys "STEEL") '("STK"))
    ((= sys "TRAY") '("Cable tray" "Trunking" "Ladder"))
    (T '("nep TDC" "nep C" "tron" "tieu am nep TDC" "cach nhiet nep TDC" "cach nhiet nep C"))))
(defun tc:list-tile (key values)
  (start_list key) (mapcar 'add_list values) (end_list))
(defun tc:ui-system (value / sys index)
  (setq sys (nth (atoi value) *tc-systems*) *tc-ui-materials* (tc:materials sys)
    index (vl-position (tc:cfg 'material) *tc-ui-materials*))
  (tc:list-tile "material" *tc-ui-materials*) (set_tile "material" (itoa (if index index 0)))
  (if (member (get_tile "layer") '("TC_PPR" "TC_UPVC" "TC_STEEL" "TC_TRAY" "TC_DUCT"))
    (set_tile "layer" (strcat "TC_" sys)))
  (if (and (tc:pipe-p sys) (not (member (atoi (get_tile "dn")) (tc:dn-values sys))))
    (set_tile "dn" (if (= sys "UPVC") "60" "25"))))
(defun tc:ui-group (value / item)
  (setq *tc-ui-group* (atoi value) *tc-ui-items* nil)
  (foreach item *tc-commands*
    (if (= (car item) *tc-ui-group*) (setq *tc-ui-items* (append *tc-ui-items* (list item)))))
  (tc:list-tile "commands" (mapcar '(lambda (item) (strcat "[" (cadr item) "] " (caddr item))) *tc-ui-items*))
  (set_tile "commands" "0") (tc:ui-hint))
(defun tc:ui-hint ( / item)
  (setq item (nth (atoi (get_tile "commands")) *tc-ui-items*))
  (if item (set_tile "hint" (nth 3 item))))
(defun tc:ui-save ( / pair key value parsed values problem sys mat)
  (foreach key '(dn width height text gap overlap fillet rowtol allowance unit)
    (setq value (distof (get_tile (strcase (vl-symbol-name key) T)) 2))
    (if (or (null value) (< value 0.0) (and (not (member key '(allowance overlap fillet))) (equal value 0.0 0.000000001)))
      (setq problem (strcat "Gia tri khong hop le: " (vl-symbol-name key)))
      (setq values (cons (cons key value) values))))
  (if (or (= (get_tile "layer") "") (not (snvalid (get_tile "layer")))) (setq problem "Ten layer khong hop le."))
  (if problem (progn (set_tile "error" problem) nil)
    (progn
      (foreach pair values (tc:set (car pair) (cdr pair)))
      (foreach key '(layer service elevation erase note) (tc:set key (get_tile (strcase (vl-symbol-name key) T))))
      (setq sys (nth (atoi (get_tile "system")) *tc-systems*) mat (nth (atoi (get_tile "material")) *tc-ui-materials*))
      (tc:set 'system sys) (tc:set 'material mat) (tc:save-config) (set_tile "error" "Da luu thong so.") T)))
(defun tc:ui-run ()
  (if (tc:ui-save)
    (progn (setq *tc-ui-command* (cadr (nth (atoi (get_tile "commands")) *tc-ui-items*))) (done_dialog 1))))
(defun tc:dcl-file ( / file stream line)
  (setq file (vl-filename-mktemp "ToolsCad-" nil ".dcl") stream (open file "w"))
  (if (null stream) (tc:fail "Khong tao duoc DCL tam. Kiem tra thu muc TEMP."))
  (foreach line *tc-dcl-lines* (write-line line stream)) (close stream) file)
(defun tc:panel ( / *error* path dialog result key index)
  (defun *error* (msg)
    (if (and dialog (>= dialog 0)) (unload_dialog dialog))
    (if path (vl-file-delete path)) (princ (strcat "\nTOOLS CAD: " msg)) (princ))
  (if (not (boundp '*tc-ui-group*)) (setq *tc-ui-group* 0))
  (setq path (tc:dcl-file) dialog (load_dialog path) result 1)
  (if (< dialog 0) (tc:fail "Khong nap duoc giao dien DCL."))
  (while (= result 1)
    (if (not (new_dialog "tc_main" dialog)) (tc:fail "Khong tao duoc bang dieu khien."))
    (tc:list-tile "groups" *tc-groups*) (set_tile "groups" (itoa *tc-ui-group*))
    (tc:list-tile "system" *tc-systems*)
    (setq index (vl-position (tc:cfg 'system) *tc-systems*)) (if (null index) (setq index 0))
    (set_tile "system" (itoa index)) (tc:ui-system (itoa index))
    (foreach key '(dn width height text gap overlap fillet rowtol allowance unit)
      (set_tile (strcase (vl-symbol-name key) T) (rtos (tc:cfg key) 2 3)))
    (foreach key '(layer service elevation erase note) (set_tile (strcase (vl-symbol-name key) T) (tc:cfg key)))
    (tc:ui-group (itoa *tc-ui-group*))
    (action_tile "groups" "(tc:ui-group $value)")
    (action_tile "system" "(tc:ui-system $value)")
    (action_tile "commands" "(if (= $reason 4) (tc:ui-run) (tc:ui-hint))")
    (action_tile "run" "(tc:ui-run)") (action_tile "save" "(tc:ui-save)")
    (action_tile "help" "(tc:help)") (action_tile "cancel" "(done_dialog 0)")
    (setq result (start_dialog))
    (if (= result 1) (apply (read (strcat "C:" *tc-ui-command*)) nil)))
  (unload_dialog dialog) (vl-file-delete path) (princ))
(defun tc:browser-filter ( / pattern name)
  (setq pattern (strcase (get_tile "query")) *tc-browser-shown* nil)
  (if (= pattern "") (setq pattern "*"))
  (if (not (wcmatch pattern "*`**,*`?*")) (setq pattern (strcat "*" pattern "*")))
  (foreach name *tc-browser-all*
    (if (wcmatch (strcase name) pattern) (setq *tc-browser-shown* (cons name *tc-browser-shown*))))
  (setq *tc-browser-shown* (reverse *tc-browser-shown*))
  (tc:list-tile "blocks" *tc-browser-shown*) (set_tile "blocks" "0")
  (set_tile "count" (strcat (itoa (length *tc-browser-shown*)) " block phu hop.")))
(defun tc:browser-accept ()
  (if *tc-browser-shown*
    (progn (setq *tc-browser-name* (nth (atoi (get_tile "blocks")) *tc-browser-shown*)) (done_dialog 1))
    (set_tile "error" "Khong co block phu hop.")))
(defun tc:browser ( / path dialog result name names)
  (setq names (append (tc:block-names (tc:dbx)) (tc:block-names (tc:doc))) *tc-browser-all* nil *tc-browser-name* nil)
  (foreach name (acad_strlsort names) (if (not (member name *tc-browser-all*)) (setq *tc-browser-all* (cons name *tc-browser-all*))))
  (setq *tc-browser-all* (reverse *tc-browser-all*) path (tc:dcl-file) dialog (load_dialog path))
  (if (and (>= dialog 0) (new_dialog "tc_blocks" dialog))
    (progn (set_tile "query" "*") (tc:browser-filter)
      (action_tile "filter" "(tc:browser-filter)") (action_tile "query" "(tc:browser-filter)")
      (action_tile "blocks" "(if (= $reason 4) (tc:browser-accept))")
      (action_tile "accept" "(tc:browser-accept)") (action_tile "cancel" "(done_dialog 0)")
      (setq result (start_dialog))))
  (if (>= dialog 0) (unload_dialog dialog)) (vl-file-delete path)
  (if (= result 1) *tc-browser-name*))
(defun tc:insert-browser ( / name point angle o scale)
  (if (setq name (tc:browser))
    (progn
      (setq scale (tc:positive "\nTy le chen" (tc:cfg 'scale)))
      (while (setq point (tc:point "\nDiem chen (Enter ket thuc): "))
        (setq angle (getangle (trans point 0 1) "\nHuong block <0>: "))
        (setq angle (if angle (tc:angle point (trans (polar (trans point 0 1) angle 1.0) 1 0)) 0.0)
          o (tc:insert name point angle (tc:layer (tc:cfg 'layer) 7)))
        (vla-put-XScaleFactor o scale) (vla-put-YScaleFactor o scale) (vla-put-ZScaleFactor o scale)))))
(defun tc:help ( / item)
  (alert (strcat "TOOLS CAD DUY - AutoCAD 2024 Windows\n\n"
    "1. APPLOAD TOOLS-CAD_DUY.lsp, go TOOLS.\n"
    "2. TCTEMPLATE: chon template CAd Duy.dwg cua ban.\n"
    "3. Chon nhom, thong so, nhap dup lenh de chay.\n"
    "4. Enter ket thuc, Esc huy; U hoan tac mot lenh.\n\n"
    "Chi thao tac Model space / WCS XY / Z=0.\n"
    "Mac dinh mm; thong ke chia 1000 ra met.\n"
    "Phu kien thieu se duoc bao ten, khong tu thay the.\n"
    "TCPPR/TCUPVC/TCSTEEL: thep nhap DN, nhua nhap D.\n"
    "TCINSPECT: xem dynamic properties va AllowedValues.\n"
    "TCSELFTEST: kiem thu trong ban ve moi rong.\n\n"
    "Ban 0.9: can chay kiem thu tren AutoCAD thuc te.\n"
    "Giao dien DCL dong khi chay lenh va mo lai khi xong."))
  (foreach item *tc-commands* (princ (strcat "\n" (cadr item) " - " (caddr item)))) (princ))
(princ)

;;; ===== tc-diagnostics =====
(defun tc:initialize ( / names)
  (setq names (tc:block-names (tc:dbx)))
  (tc:mline-style)
  (princ (strcat "\nThu vien: " (tc:library-path) "\n" (itoa (length names))
    " block co ten. Nhap tung block khi can; khong chen nguyen ban ve mau.")))
(defun tc:diagnostics ( / path item missing)
  (princ (strcat "\nTOOLS CAD " *tc-version* " | AutoCAD " (getvar "ACADVER")
    " | platform=" (getvar "PLATFORM") " | LISPSYS=" (itoa (getvar "LISPSYS"))))
  (princ "\nHo tro AutoCAD Windows ban day du; chua ho tro AutoCAD LT/macOS.")
  (setq path (tc:library-path))
  (if path (princ (strcat "\nTemplate: " path)) (princ "\nChua chon template. Go TCTEMPLATE."))
  (princ (strcat "\nModel space=" (if (> (getvar "CVPORT") 1) "OK" "CAN CHUYEN SANG MODEL")
    " | Don vi ve/met=" (rtos (tc:cfg 'unit) 2 3)))
  (princ "\nDung TCINIT de kiem tra ObjectDBX; TCSELFTEST de chay thu tren ban ve moi."))
(defun tc:assert (condition message)
  (if condition (progn (setq *tc-test-count* (1+ *tc-test-count*))
    (princ (strcat "\nPASS " (itoa *tc-test-count*) ": " message)))
    (tc:fail (strcat "SELFTEST FAIL: " message))))
(defun tc:selftest-body ( / sys y pts obj seg test cases case result fit)
  (setq *tc-test-count* 0)
  (tc:assert (= (tc:corner '(0.0 0.0 0.0) '(1000.0 0.0 0.0) '(1000.0 1000.0 0.0)) 90) "Nhan dien co 90")
  (tc:assert (null (tc:corner '(0.0 0.0 0.0) '(1000.0 0.0 0.0) '(1200.0 1000.0 0.0))) "Tu choi goc khong ho tro")
  (tc:set 'note "0") (tc:set 'layer "TC_SELFTEST") (tc:set 'width 200.0) (tc:set 'height 100.0)
  (tc:layer "TC_SELFTEST" 4)
  (setq cases '(("PPR" "PPR" 25.0) ("UPVC" "UPVC" 60.0) ("STEEL" "STK" 25.0)
    ("TRAY" "Cable tray" 0.0) ("DUCT" "nep TDC" 0.0) ("DUCT" "tron" 0.0)) y 0.0)
  (foreach case cases
    (setq sys (car case)) (tc:set 'system sys) (tc:set 'material (cadr case)) (tc:set 'dn (caddr case))
    (setq pts (list (list 0.0 y 0.0) (list 4000.0 y 0.0) (list 4000.0 (+ y 4000.0) 0.0)
                   (list 8000.0 (+ y 8000.0) 0.0)))
    (tc:build-sized-route pts (list (list (caddr case) 200.0 100.0) (list (caddr case) 200.0 100.0)
      (list (caddr case) 200.0 100.0)) sys)
    (tc:assert T (strcat "Tao tuyen + cong noi hinh hoc " sys " / " (cadr case)))
    (setq y (+ y 12000.0)))
  (tc:set 'system "PPR") (tc:set 'material "PPR")
  (tc:build-sized-route '((12000.0 5000.0 0.0) (16000.0 5000.0 0.0) (20000.0 5000.0 0.0) (20000.0 9000.0 0.0))
    '((32.0 200.0 100.0) (25.0 200.0 100.0) (25.0 200.0 100.0)) "PPR")
  (tc:assert T "Doi Size PPR 32 -> 25 va noi co 90")
  (setq obj (tc:straight '(12000.0 0.0 0.0) '(17000.0 0.0 0.0) "PPR" "PPR" 25.0 0.0 0.0 "TC_SELFTEST"))
  (tc:assert (equal (tc:entity-length obj) 5000.0 0.000001) "Thong ke MLINE 5000 mm")
  (tc:assert (= (tc:xget obj "TC_SYSTEM") "PPR") "Doc/ghi XData")
  (setq obj (tc:straight '(12000.0 1000.0 0.0) '(17000.0 1000.0 0.0) "TRAY" "Cable tray" 0.0 300.0 100.0 "TC_SELFTEST"))
  (tc:assert (equal (tc:dyn obj "Length") 5000.0 0.000001) "Ghi dynamic Length")
  (tc:assert (equal (tc:dyn obj "Width1") 300.0 0.000001) "Ghi dynamic Width1")
  (tc:assert (equal (tc:entity-length obj) 5000.0 0.000001) "Doc chieu dai block dong")
  (tc:assert (= (cdr (assoc "CABLETRAY" (tc:attributes obj))) "W300xH100") "Gan thuoc tinh SIZE theo tag thuc te")
  (setq obj (tc:aligned-dim '(12000.0 0.0 0.0) '(17000.0 0.0 0.0) '(12000.0 -1000.0 0.0) "TC_SELFTEST"))
  (tc:assert (equal (vla-get-Measurement obj) 5000.0 0.000001) "Tao DIM do duoc 5000 mm")
  (princ (strcat "\nSELFTEST PASS: " (itoa *tc-test-count*) " checks. Kiem tra truc quan cac tuyen vua tao.")))
(defun tc:selftest ( / saved result)
  (if (or (/= (vla-get-Count (tc:space)) 0) (/= (getvar "DBMOD") 0))
    (tc:fail "TCSELFTEST chi chay trong ban ve Model rong, chua sua. Mo NEW truoc."))
  (setq saved *tc-settings* result (vl-catch-all-apply 'tc:selftest-body nil) *tc-settings* saved)
  (if (vl-catch-all-error-p result)
    (tc:fail (if *tc-failure* *tc-failure* (vl-catch-all-error-message result)))))
(princ)

;;; ===== tc-commands =====
;;; Generated command registry; edit tools/build_release.py and rebuild.
(setq *tc-commands* (list
  (list 0 "TCPPR" "Ve ong PPR" "Pick diem hoac chon Polyline; tu chen co 45/90.")
  (list 0 "TCUPVC" "Ve ong UPVC" "Duong kinh ngoai D; vat lieu theo template Duy.")
  (list 0 "TCSTEEL" "Ve ong thep" "Nhap DN; ve MLINE theo D ngoai va fitting DN.")
  (list 0 "TCTRAY" "Ve mang cap" "Cable tray / Trunking / Ladder, Width1 va Length.")
  (list 0 "TCDUCT" "Ve ong gio" "Nep TDC / nep C / tron / cach nhiet / tieu am.")
  (list 0 "TCPPRPL" "Polyline sang PPR" "Chuyen nhieu polyline mo, doan thang.")
  (list 0 "TCUPVCPL" "Polyline sang UPVC" "Giu nguon mac dinh; co the bat xoa nguon.")
  (list 0 "TCSTEELPL" "Polyline sang thep" "Kiem tra tat ca nguon truoc khi tao tuyen.")
  (list 0 "TCTRAYPL" "Polyline sang mang cap" "Dung block dong thuc te cua template.")
  (list 0 "TCDUCTPL" "Polyline sang ong gio" "Ong gio tron dung Diameter, chu nhat dung Width1.")
  (list 0 "TCSPLITDUCT" "Chia doan ong gio" "Chia theo chieu dai; giu dynamic, attributes va XData.")
  (list 0 "TCLINETRAY" "Net song song sang mang" "Nhom LINE song song va chong lan theo chieu doc.")
  (list 1 "TCAFPPR" "Tu noi fitting PPR" "Pair/Batch: co 45/90, tee, reducer; bao block thieu.")
  (list 1 "TCAFUPVC" "Tu noi fitting UPVC" "MLINE 2 dinh, tam Zero; cat theo mep fitting.")
  (list 1 "TCAFSTEEL" "Tu noi fitting thep" "D ngoai MLINE doi sang DN de chon fitting.")
  (list 1 "TCAFTRAY" "Tu noi fitting mang" "Elbow / Tee / Cross / Reducer, ke ca Batch.")
  (list 1 "TCAFDUCT" "Tu noi fitting ong gio" "Co / Chac 3 / Con giam; chi dung block co trong template.")
  (list 1 "TCFIT" "Chen phu kien thu cong" "Theo he va thong so ben phai, hoac nhap ten block.")
  (list 1 "TCUP90" "Cap co UP90 + UP45" "Pick gan dau MLINE UPVC; giong mo-dun goc.")
  (list 1 "TCDN45" "Co thoat xuong DN45" "Trang thai Duy la DN45, khong phai DOWN45.")
  (list 1 "TCDRAIN" "Noi nhanh polyline thoat" "Ong chinh + nhanh vuong goc; vat ve huong ong dung.")
  (list 1 "TCCHAMFER" "Vat goc polyline 45" "Vat cac dinh 90; giu nguon mac dinh.")
  (list 2 "TCBLOCK" "Thu vien / chen block" "Loc 1315 block co ten trong template va block ban ve.")
  (list 2 "TCARRAY" "Bo tri block theo vung" "Nhap so hang/cot hoac buoc; sao chep dynamic cua mau.")
  (list 2 "TCALIGN" "Can hang / chia deu block" "Giu nguyen block neo, chieu len truc hoac chia deu.")
  (list 2 "TCREPLACE" "Thay block" "Theo selection/ten; giu tag trung, scale, goc, XData.")
  (list 2 "TCRENAME" "Doi ten dinh nghia block" "Anh huong tat ca tham chieu cung dinh nghia.")
  (list 2 "TCBALIGN" "Chen block theo tiep tuyen" "Chon block mau, pick tren LINE/POLYLINE/ARC.")
  (list 2 "TCBEDIT" "Sua dynamic property" "Hien AllowedValues va kiem tra lai sau khi gan.")
  (list 2 "TCATTR" "Sua attribute hang loat" "Lay tag tu block mau, gan gia tri cho nhom da chon.")
  (list 2 "TCBBOX" "Khung block hien tai" "Lay hinh hoc hien thi, bo qua text va attribute.")
  (list 2 "TCBYLAYER" "Chuan hoa layer / mau" "Tuy chon sua ruot block; mac dinh chi sua tham chieu.")
  (list 3 "TCGRID" "Noi block ngang doc" "Thu tu diem gan nhat, tao polyline ortho.")
  (list 3 "TCCHAIN" "Noi block gan nhat" "Chuoi polyline qua diem chen, khong bo goc.")
  (list 3 "TCFILLET" "Noi block va bo goc" "Polyine qua block, R theo thong so dung chung.")
  (list 3 "TCZIGZAG" "Noi block zigzag" "Nhom hang theo sai so, sap xep kieu ran.")
  (list 3 "TCZIGBOX" "Zigzag va hop chia" "Dung HopchiangD20V1 scale 2 va Options cua block.")
  (list 3 "TCARC" "Day dien dang cung" "Bulge tinh theo do vong cung that.")
  (list 3 "TCULINK" "Noi o cam kieu U" "Pick truc day, noi tung cap va bo goc.")
  (list 3 "TCSPINE" "Truc chinh va nhanh block" "Chieu block len truc qua diem pick.")
  (list 3 "TCDB" "Noi thiet bi ve tu dien" "Giu du cac dinh cua polyline truc chinh.")
  (list 4 "TCDIMBLOCK" "DIM chuoi block" "DIM xoay theo truc, tuy chon them DIM tong.")
  (list 4 "TCDIM" "DIM cac doan tuyen" "LINE / polyline thang / MLINE / block thang.")
  (list 4 "TCLABEL" "Text doc tuyen" "Dat text o nua chieu dai that, xoay de doc.")
  (list 4 "TCLEADER" "Ghi chu MLeader" "Chon mui ten, diem ghi chu, nhap noi dung.")
  (list 5 "TCSTAT" "Thong ke tong hop" "Tach vat lieu, he thong, layer, size, visibility.")
  (list 5 "TCPPRSTAT" "Thong ke PPR" "Loc nhom PPR tu metadata va ten fitting.")
  (list 5 "TCUPVCSTAT" "Thong ke UPVC" "Dem fitting va tinh chieu dai ong.")
  (list 5 "TCSTEELSTAT" "Thong ke thep" "Dem fitting DN va tinh chieu dai MLINE.")
  (list 5 "TCTRAYSTAT" "Thong ke mang cap" "Dem block, gom tong Length cac block thang.")
  (list 5 "TCDUCTSTAT" "Thong ke ong gio" "Size theo thuoc tinh block; chia don vi ra met.")
  (list 5 "TCCABLESTAT" "Thong ke day cap" "Chieu dai tuyen + day cho moi tuyen.")
  (list 5 "TCSUMDIM" "Cong DIM thang" "Bo qua DIM goc/ban kinh; xuat bang chi tiet.")
  (list 5 "TCTABLECSV" "Bang CAD sang CSV" "CSV UTF-8 BOM, Excel mo duoc, khong can cai Excel.")
  (list 6 "TCXSET" "Gan XData" "Chon ten nhom va noi dung, gan cho selection.")
  (list 6 "TCXGET" "Doc XData" "Doc metadata cua selection ra dong lenh.")
  (list 6 "TCISO" "Ban sao 2.5D" "Xoay/ep Y theo test.bas; khong phai mo hinh BIM 3D.")
  (list 6 "TCINSPECT" "Xem block / AllowedValues" "In ten, dynamic properties, attributes va XData.")
  (list 6 "TCTEMPLATE" "Chon template Duy" "Luu duong dan thu vien tren may Windows cua ban.")
  (list 6 "TCINIT" "Khoi tao / kiem tra thu vien" "Doc danh muc ObjectDBX va tao style TC_MC.")
  (list 6 "TCCHECK" "Chan doan moi truong" "In phien ban, LISPSYS, template va don vi.")
  (list 6 "TCSELFTEST" "Kiem thu AutoCAD" "Chi chay trong ban ve moi rong; tao hinh de doi chieu.")
))
(defun C:TCPPR () (tc:run '(lambda () (tc:draw "PPR"))))
(defun C:TCUPVC () (tc:run '(lambda () (tc:draw "UPVC"))))
(defun C:TCSTEEL () (tc:run '(lambda () (tc:draw "STEEL"))))
(defun C:TCTRAY () (tc:run '(lambda () (tc:draw "TRAY"))))
(defun C:TCDUCT () (tc:run '(lambda () (tc:draw "DUCT"))))
(defun C:TCPPRPL () (tc:run '(lambda () (tc:convert "PPR"))))
(defun C:TCUPVCPL () (tc:run '(lambda () (tc:convert "UPVC"))))
(defun C:TCSTEELPL () (tc:run '(lambda () (tc:convert "STEEL"))))
(defun C:TCTRAYPL () (tc:run '(lambda () (tc:convert "TRAY"))))
(defun C:TCDUCTPL () (tc:run '(lambda () (tc:convert "DUCT"))))
(defun C:TCSPLITDUCT () (tc:run '(lambda () (tc:split-duct))))
(defun C:TCLINETRAY () (tc:run '(lambda () (tc:line-to-tray))))
(defun C:TCAFPPR () (tc:run '(lambda () (tc:autofit "PPR"))))
(defun C:TCAFUPVC () (tc:run '(lambda () (tc:autofit "UPVC"))))
(defun C:TCAFSTEEL () (tc:run '(lambda () (tc:autofit "STEEL"))))
(defun C:TCAFTRAY () (tc:run '(lambda () (tc:autofit "TRAY"))))
(defun C:TCAFDUCT () (tc:run '(lambda () (tc:autofit "DUCT"))))
(defun C:TCFIT () (tc:run '(lambda () (tc:manual-fitting))))
(defun C:TCUP90 () (tc:run '(lambda () (tc:upvc-rise T))))
(defun C:TCDN45 () (tc:run '(lambda () (tc:upvc-rise nil))))
(defun C:TCDRAIN () (tc:run '(lambda () (tc:drain-connect))))
(defun C:TCCHAMFER () (tc:run '(lambda () (tc:chamfer))))
(defun C:TCBLOCK () (tc:run '(lambda () (tc:insert-browser))))
(defun C:TCARRAY () (tc:run '(lambda () (tc:block-grid))))
(defun C:TCALIGN () (tc:run '(lambda () (tc:block-align))))
(defun C:TCREPLACE () (tc:run '(lambda () (tc:block-replace))))
(defun C:TCRENAME () (tc:run '(lambda () (tc:block-rename))))
(defun C:TCBALIGN () (tc:run '(lambda () (tc:insert-aligned))))
(defun C:TCBEDIT () (tc:run '(lambda () (tc:block-edit))))
(defun C:TCATTR () (tc:run '(lambda () (tc:attribute-edit))))
(defun C:TCBBOX () (tc:run '(lambda () (tc:bounding-box))))
(defun C:TCBYLAYER () (tc:run '(lambda () (tc:bylayer))))
(defun C:TCGRID () (tc:run '(lambda () (tc:electrical "GRID"))))
(defun C:TCCHAIN () (tc:run '(lambda () (tc:electrical "CHAIN"))))
(defun C:TCFILLET () (tc:run '(lambda () (tc:electrical "FILLET"))))
(defun C:TCZIGZAG () (tc:run '(lambda () (tc:electrical "ZIGZAG"))))
(defun C:TCZIGBOX () (tc:run '(lambda () (tc:electrical "BOX"))))
(defun C:TCARC () (tc:run '(lambda () (tc:electrical "ARC"))))
(defun C:TCULINK () (tc:run '(lambda () (tc:offset-links nil))))
(defun C:TCSPINE () (tc:run '(lambda () (tc:offset-links T))))
(defun C:TCDB () (tc:run '(lambda () (tc:panel-route))))
(defun C:TCDIMBLOCK () (tc:run '(lambda () (tc:dim-blocks))))
(defun C:TCDIM () (tc:run '(lambda () (tc:dim-segments))))
(defun C:TCLABEL () (tc:run '(lambda () (tc:curve-text))))
(defun C:TCLEADER () (tc:run '(lambda () (tc:leader))))
(defun C:TCSTAT () (tc:run '(lambda () (tc:statistics nil nil))))
(defun C:TCPPRSTAT () (tc:run '(lambda () (tc:statistics "PPR" nil))))
(defun C:TCUPVCSTAT () (tc:run '(lambda () (tc:statistics "UPVC" nil))))
(defun C:TCSTEELSTAT () (tc:run '(lambda () (tc:statistics "STEEL" nil))))
(defun C:TCTRAYSTAT () (tc:run '(lambda () (tc:statistics "TRAY" nil))))
(defun C:TCDUCTSTAT () (tc:run '(lambda () (tc:statistics "DUCT" nil))))
(defun C:TCCABLESTAT () (tc:run '(lambda () (tc:statistics nil T))))
(defun C:TCSUMDIM () (tc:run '(lambda () (tc:dimension-total))))
(defun C:TCTABLECSV () (tc:run '(lambda () (tc:export-tables))))
(defun C:TCXSET () (tc:run '(lambda () (tc:xdata-edit T))))
(defun C:TCXGET () (tc:run '(lambda () (tc:xdata-edit nil))))
(defun C:TCISO () (tc:run '(lambda () (tc:iso))))
(defun C:TCINSPECT () (tc:run '(lambda () (tc:inspect))))
(defun C:TCTEMPLATE () (tc:run '(lambda () (tc:select-template))))
(defun C:TCINIT () (tc:run '(lambda () (tc:initialize))))
(defun C:TCCHECK () (tc:run '(lambda () (tc:diagnostics))))
(defun C:TCSELFTEST () (tc:run '(lambda () (tc:selftest))))
(defun C:TOOLS () (tc:panel))
(defun C:TC () (tc:panel))
(defun C:TCHELP () (tc:help))
(defun C:SHOWFORM () (C:TOOLS))
(defun C:MAINPPR () (C:TCPPR))
(defun C:VEONGUPVC () (C:TCUPVC))
(defun C:MAINSTEEL () (C:TCSTEEL))
(defun C:MAINMANGCAP () (C:TCTRAY))
(defun C:MAINDUCT () (C:TCDUCT))
(defun C:BOTRIBLOCK () (C:TCARRAY))
(defun C:ALIGNANDSPACEBLOCKS () (C:TCALIGN))
(defun C:CHANGEBLOCK () (C:TCREPLACE))
(defun C:REPLACEBLOCKNAMES () (C:TCREPLACE))
(defun C:INSERTBLOCKWITHROTATION () (C:TCBLOCK))
(defun C:DRAWCURRENTVISIBILITYBOUNDINGBOXFIXED () (C:TCBBOX))
(defun C:AUTOTRAYFITTING_FULL () (C:TCAFTRAY))
(defun C:AUTOINSERTFITTING_PPR () (C:TCAFPPR))
(defun C:AUTOINSERTFITTING_STEEL () (C:TCAFSTEEL))
(defun C:AUTOINSERTFITTING_FINAL_STANDARD_V11 () (C:TCAFUPVC))
(defun C:AUTOINSERTFITTING_FINAL_STANDARD_V10 () (C:TCAFUPVC))
(defun C:AUTOINSERTFITTING_BATCH_FULL () (C:TCAFUPVC))
(defun C:INSERTDOUBLEELBOWONMLINE () (C:TCUP90))
(defun C:ELBOW45DOWNONMLINE () (C:TCDN45))
(defun C:CONVERTPOLYLINETOPIPING () (C:TCPPRPL))
(defun C:VEONGTHOAT_POLYLINE () (C:TCUPVCPL))
(defun C:VEONGSTEEL_POLYLINE () (C:TCSTEELPL))
(defun C:VEMANGCAP_FROM_POLYLINE () (C:TCTRAYPL))
(defun C:SPLITDUCTBLOCKS () (C:TCSPLITDUCT))
(defun C:SCANANDGROUP_INSERTCABLETRAY () (C:TCLINETRAY))
(defun C:CONNECTBLOCKSGRID () (C:TCGRID))
(defun C:CONNECTBLOCKSSINGLEPOLYLINE_FILLET () (C:TCFILLET))
(defun C:CONNECTBLOCKSGRIDZIGZAG () (C:TCZIGZAG))
(defun C:CONNECTBLOCKSGRIDZIGZAGWITHBOX () (C:TCZIGBOX))
(defun C:LINKBLOCKSARC_AUTOSORT_NEARESTEND () (C:TCARC))
(defun C:LINKBLOCKOFFSET () (C:TCULINK))
(defun C:CREATECHAINPOLYLINEFROMBLOCKS () (C:TCSPINE))
(defun C:CONNECTBLOCKS_FOLLOWORCREATEPOLYLINE () (C:TCDB))
(defun C:QUICKCHAINDIMBLOCKS_FINAL () (C:TCDIMBLOCK))
(defun C:QUICKCHAINDIMBLOCKS_SAFE () (C:TCDIMBLOCK))
(defun C:DIMALLPOLYLINESINSELECTION () (C:TCDIM))
(defun C:DIMMLINE_FINAL_CORRECTSIDE () (C:TCDIM))
(defun C:DIMLENGTHOFBLOCK () (C:TCDIM))
(defun C:TINHTONGDIM_CHITIET () (C:TCSUMDIM))
(defun C:TINHTONGDIM_XUATTABLE () (C:TCSUMDIM))
(defun C:EXPORTTABLESTOEXCEL () (C:TCTABLECSV))
(defun C:CREATEMLEADER_CUSTOM () (C:TCLEADER))
(defun C:COUNTALL_WITHMLINE () (C:TCSTAT))
(defun C:TRUYVAN () (C:TCXGET))
(defun C:THONGKEPOLYLINE () (C:TCCABLESTAT))
(defun C:THONGKECAP () (C:TCCABLESTAT))
(defun C:THONGKEDUCT_TOTABLE () (C:TCDUCTSTAT))
(defun C:COUNTBLOCKSBYATTRIBUTES_TOTABLE () (C:TCTRAYSTAT))
(defun C:COUNTBLOCKSANDMLINE_TOTABLE_WITHSYSTEM () (C:TCSTAT))
(defun C:COUNTBLOCKSANDMLINE_TOTABLE_STEEL () (C:TCSTEELSTAT))
(defun C:COUNTBLOCKSANDMLINE_TOTABLE_THOAT () (C:TCUPVCSTAT))
(defun C:COUNTBLOCKSANDMLINE_TOTABLE () (C:TCPPRSTAT))
(defun C:BTN_CLEANANDPURGE () (C:TCBYLAYER))
(defun C:CHUYEN2D_SANG_25D_FIXED () (C:TCISO))
(defun C:TAOMATNGHIENG_25D_ISOMETRIC () (C:TCISO))
(defun C:AUTOCONNECT_V15_PHASED () (C:TCDRAIN))
(defun C:DATPHUKIEN () (C:TCFIT))
(princ)

(princ "\nTOOLS CAD DUY 0.9 | Go TOOLS de mo bang dieu khien, TCTEMPLATE de chon thu vien.")
(princ)
